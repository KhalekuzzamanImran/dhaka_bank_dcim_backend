ENVIROMUX2D DEFINITIONS ::= BEGIN
IMPORTS
   NOTIFICATION-GROUP, OBJECT-GROUP             FROM SNMPv2-CONF
   MODULE-IDENTITY, OBJECT-TYPE, 
   NOTIFICATION-TYPE, enterprises,
   Integer32                                    FROM  SNMPv2-SMI
   DisplayString                                FROM  SNMPv2-TC;
      
enviromux2D MODULE-IDENTITY
     LAST-UPDATED "201904251400Z"
     ORGANIZATION "Network Technologies Inc."
     CONTACT-INFO 
         "Network Technologies Inc.
         
          Postal: 1275 Danner Dr,
                  Aurora, OH 442022
                  US
                 
          Tel: 330-562-7070
          Fax: 330-562-1999
             
          WEB: www.networktechinc.com"
	 
     DESCRIPTION 
         "ENVIROMUX-2D MIB file." 
     REVISION     "201904251400Z"
         DESCRIPTION "Rev. 1.19 - Defined remote digital input and remote relay traps"
     REVISION     "201810011600Z" 
         DESCRIPTION  "Rev. 1.18 - Added ALDS Sensor and fixed MIB file errors"  
     REVISION     "201804141500Z" 
         DESCRIPTION  "Rev. 1.16 - Enable network security"  
     REVISION     "201803051000Z" 
         DESCRIPTION  "Rev. 1.15 - software reset/network config"  
     REVISION     "201712101600Z" 
         DESCRIPTION  "Rev. 1.14 - add writable sensor threshold"    
     REVISION     "201711281600Z" 
         DESCRIPTION  "Rev. 1.13 - add firmware version; add writable message registers"    
     REVISION     "201708081500Z" 
         DESCRIPTION  "Rev. 1.12 - Change alert/event status registers to be read-write"    
     REVISION     "201611201400Z" 
         DESCRIPTION  "Rev. 1.11 - Added type definitions for ACLM3 sensors"    
     REVISION     "201609031400Z" 
         DESCRIPTION  "Rev. 1.10 - Added definitions for warning thresholds"    
     REVISION     "201603041400Z" 
         DESCRIPTION  "Rev. 1.09 - Added Auxiliary 2 sensors"    
     REVISION     "201510141400Z" 
         DESCRIPTION  "Rev. 1.08 - Added ACDC sensors"    
     REVISION     "201411171400Z" 
         DESCRIPTION  "Rev. 1.07 - Added IP sensors"    
     REVISION     "201403171400Z" 
         DESCRIPTION  "Rev. 1.06 - Fixed compile errors or warnings"    
     REVISION     "201312041400Z" 
         DESCRIPTION  "Rev. 1.05 - Fixed attributes for OIDs, made relays writable"    
     REVISION     "201305091400Z" 
         DESCRIPTION  "Rev. 1.04 - Changes for Tac sensor on Digital input 1"            
    REVISION     "201304251400Z" 
         DESCRIPTION  "Rev. 1.03 - Changes for high accuracy temperature humidity sensor"                                
    REVISION     "201302040000Z" 
         DESCRIPTION  "Rev. 1.02 - Changes for REV C pcb;Added Smoke Detectors"                                
    REVISION     "201212121400Z" 
         DESCRIPTION  "Rev. 1.01 - added remote inputs and remote relays;Added Events and Smart Alerts"
    REVISION     "201211200000Z" 
         DESCRIPTION  "Rev. 1.00 - Initial version"
     ::= { hardware 9 }

-- the root of the subtree for Network Technologies Inc
nti		        OBJECT IDENTIFIER ::= { enterprises 3699 }

-- subtree for products
products		        OBJECT IDENTIFIER ::= { nti 1 }
hardware		        OBJECT IDENTIFIER ::= { products 1 }
software		        OBJECT IDENTIFIER ::= { products 2 }
otherProduct            OBJECT IDENTIFIER ::= { hardware 200 }

-- ipdus2 subtree
masterUnit	            OBJECT IDENTIFIER ::= { enviromux2D 1 }
envTraps                OBJECT IDENTIFIER ::= { enviromux2D 100 }
hostSystem              OBJECT IDENTIFIER ::= { masterUnit 1 }
users                   OBJECT IDENTIFIER ::= { masterUnit 2 }
intSensors		        OBJECT IDENTIFIER ::= { masterUnit 3 }
auxSensors              OBJECT IDENTIFIER ::= { masterUnit 4 }
extSensors		        OBJECT IDENTIFIER ::= { masterUnit 5 }
digInputs               OBJECT IDENTIFIER ::= { masterUnit 6 }
ipDevices 		        OBJECT IDENTIFIER ::= { masterUnit 7 }
outRelays 		        OBJECT IDENTIFIER ::= { masterUnit 8 }
pwrSupplies 	        OBJECT IDENTIFIER ::= { masterUnit 9 }
events                  OBJECT IDENTIFIER ::= { masterUnit 10 }
smartAlerts             OBJECT IDENTIFIER ::= { masterUnit 11 }
remoteInputs            OBJECT IDENTIFIER ::= { masterUnit 12 }
remoteRelays            OBJECT IDENTIFIER ::= { masterUnit 13 }
smokeDetectors          OBJECT IDENTIFIER ::= { masterUnit 14 }
tacSensors              OBJECT IDENTIFIER ::= { masterUnit 15 }
ipSensors               OBJECT IDENTIFIER ::= { masterUnit 16 }
aux2Sensors             OBJECT IDENTIFIER ::= { masterUnit 17 }
msgRegisters            OBJECT IDENTIFIER ::= { masterUnit 18 }
netConfRegisters        OBJECT IDENTIFIER ::= { masterUnit 20 }
envGroups               OBJECT IDENTIFIER ::= { masterUnit 200 }

-- groups

sysGroup                OBJECT-GROUP
    OBJECTS             { sysTime, sysEnterpriseName, sysEnterpriseLocation, sysEnterpriseBranch, sysEnterpriseContact, sysEnterpriseRack, sysEnterpriseContact, sysEnterprisePhone, firmwareVersion, deviceModel, sysReset, devSerialNum, devHardwareRev, devManufacturer}
    STATUS              current
    DESCRIPTION         "System parameters group"
    ::= {envGroups 1}

intSensorsGrp           OBJECT-GROUP
    OBJECTS             { intSensorIndex, intSensorType, intSensorDescription, intSensorGroupNb, intSensorGroup,
                        intSensorValue, intSensorUnit, intSensorUnitName, intSensorStatus, intSensorMinThreshold, intSensorMaxThreshold }
    STATUS              current
    DESCRIPTION         "External sensors group"
    ::= {envGroups 2}

extSensorsGrp           OBJECT-GROUP
    OBJECTS             { extSensorIndex, extSensorType, extSensorDescription, extSensorConnector, extSensorGroupNb, extSensorGroup,
                        extSensorValue, extSensorUnit, extSensorUnitName, extSensorStatus, extSensorMinThreshold, extSensorMaxThreshold }
    STATUS              current
    DESCRIPTION         "External sensors group"
    ::= {envGroups 3}

digInputsGrp            OBJECT-GROUP
    OBJECTS             { digInputIndex, digInputType, digInputDescription, digInputConnector, digInputGroupNb, digInputGroup,
                        digInputValue, digInputStatus, digInputNormalValue }
    STATUS              current
    DESCRIPTION         "Dry contacts group"
    ::= {envGroups 5}

ipDeviceGrp            OBJECT-GROUP
    OBJECTS             { ipDeviceIndex, ipDeviceAddress, ipDeviceDescription, ipDeviceGroupNb, ipDeviceGroup, ipDeviceTimeout, ipDeviceRetries, 
                        ipDeviceValue, ipDeviceStatus }
    STATUS              current
    DESCRIPTION         "IP devices group"
    ::= {envGroups 6}

outRelaysGrp           OBJECT-GROUP
    OBJECTS             { outRelayIndex, outRelayDescription, outRelayStatus }
    STATUS              current
    DESCRIPTION         "Dry contacts group"
    ::= {envGroups 7}

miscTrapFields          OBJECT-GROUP
    OBJECTS             { envTrapDescription, envTrapValue }
    STATUS              current
    DESCRIPTION         "General Information Traps"
    ::= {envGroups 8}

intSensorTrapGrp        NOTIFICATION-GROUP
    NOTIFICATIONS       { intSensor1Trap }
    STATUS              current
    DESCRIPTION         "Internal Sensors Traps Group"
    ::= {envGroups 9}
    
extSensorTrapGrp        NOTIFICATION-GROUP
    NOTIFICATIONS       { extSensor1Trap,  extSensor2Trap,  extSensor3Trap,  extSensor4Trap }
    STATUS              current
    DESCRIPTION         "External Sensors Traps Group"
    ::= {envGroups 10}
    
digInputTrapGrp        NOTIFICATION-GROUP
    NOTIFICATIONS       { digInput1Trap, digInput2Trap, digInput3Trap, digInput4Trap, digInput5Trap }
    STATUS              current
    DESCRIPTION         "External Sensors Traps Group"
    ::= {envGroups 12}

ipDeviceTrapGrp        NOTIFICATION-GROUP
    NOTIFICATIONS       { ipDevice1Trap,  ipDevice2Trap,  ipDevice3Trap,  ipDevice4Trap,  ipDevice5Trap,  ipDevice6Trap,  ipDevice7Trap,  ipDevice8Trap, 
                          ipDevice9Trap,  ipDevice10Trap, ipDevice11Trap, ipDevice12Trap, ipDevice13Trap, ipDevice14Trap, ipDevice15Trap, ipDevice16Trap, 
                          ipDevice17Trap, ipDevice18Trap, ipDevice19Trap, ipDevice20Trap, ipDevice21Trap, ipDevice22Trap, ipDevice23Trap, ipDevice24Trap, 
                          ipDevice25Trap, ipDevice26Trap, ipDevice27Trap, ipDevice28Trap, ipDevice29Trap, ipDevice30Trap, ipDevice31Trap, ipDevice32Trap, 
                          ipDevice33Trap, ipDevice34Trap, ipDevice35Trap, ipDevice36Trap, ipDevice37Trap, ipDevice38Trap, ipDevice39Trap, ipDevice40Trap, 
                          ipDevice41Trap, ipDevice42Trap, ipDevice43Trap, ipDevice44Trap, ipDevice45Trap, ipDevice46Trap, ipDevice47Trap, ipDevice48Trap, 
                          ipDevice49Trap, ipDevice50Trap, ipDevice51Trap, ipDevice52Trap, ipDevice53Trap, ipDevice54Trap, ipDevice55Trap, ipDevice56Trap, 
                          ipDevice57Trap, ipDevice58Trap, ipDevice59Trap, ipDevice60Trap, ipDevice61Trap, ipDevice62Trap, ipDevice63Trap, ipDevice64Trap }
    STATUS              current
    DESCRIPTION         "IP Device Traps Group"
    ::= {envGroups 13}

miscNotificationGrp    NOTIFICATION-GROUP
    NOTIFICATIONS       { evLogFileTrap, dataLogFileTrap, remoteDataLogFileTrap}
    STATUS              current
    DESCRIPTION         "Other Traps Group"
    ::= {envGroups 14}

pwrSuppliesGrp         OBJECT-GROUP     
    OBJECTS             { pwrSupplyIndex, pwrSupplyStatus }
    STATUS              current
    DESCRIPTION         "Power supplies group"
    ::= {envGroups 15}

msgRegistersGrp         OBJECT-GROUP
    OBJECTS             { msgRegistersIndex, msgRegistersDescription, msgRegistersStatus }
    STATUS              current
    DESCRIPTION         "message registers group"
    ::= {envGroups 16}

netConfRegistersGrp     OBJECT-GROUP
    OBJECTS             { netConfIPv4Mode, netConfIPv4Addr, netConfIPv4Mask, netConfIPv4Gateway, netConfPreDNS, netConfAltDNS, netConfDNSTimeout, 
						  netConfIPv6Mode, netConfIPv6Addr, netConfIPv6Gateway, netConfEnable6to4Tunnel, netConfLocalIPAddr, netConfRemoteIPv4Addr, netConfVlanEnabled, netConfVlanID, netConfSave, netConfEnableSecurity}
    STATUS              current
    DESCRIPTION         "network configure registers group"
    ::= {envGroups 18}


remoteRelaysGrp           OBJECT-GROUP
    OBJECTS             { remoteRelayIndex, remoteRelayDescription, remoteRelayStatus }
    STATUS              current
    DESCRIPTION         "Remote Output Relay group"
    ::= {envGroups 19}

remoteInputsGrp            OBJECT-GROUP
    OBJECTS             { remoteInputIndex, remoteInputType, remoteInputDescription, remoteInputConnector, remoteInputGroupNb, remoteInputGroup,
                        remoteInputValue, remoteInputStatus, remoteInputNormalValue }
    STATUS              current
    DESCRIPTION         "Dry Contact group"
    ::= {envGroups 20}

remoteInputTrapGrp        NOTIFICATION-GROUP
    NOTIFICATIONS       {   remoteInput1Trap,   remoteInput2Trap,   remoteInput3Trap,   remoteInput4Trap,   remoteInput5Trap, remoteInput6Trap, remoteInput7Trap, remoteInput8Trap, 
                            remoteInput9Trap,   remoteInput10Trap,  remoteInput11Trap,  remoteInput12Trap,  remoteInput13Trap,  remoteInput14Trap,  remoteInput15Trap, 
                            remoteInput16Trap}
    STATUS              current
    DESCRIPTION         "Dry Contact group"
    ::= {envGroups 21}

remoteRelayTrapGrp          NOTIFICATION-GROUP
    NOTIFICATIONS       {   remoteRelay1Trap, remoteRelay2Trap, remoteRelay3Trap, remoteRelay4Trap, remoteRelay5Trap, remoteRelay6Trap, remoteRelay7Trap, remoteRelay8Trap, 
                            remoteRelay9Trap, remoteRelay10Trap, remoteRelay11Trap, remoteRelay12Trap, remoteRelay13Trap, remoteRelay14Trap, remoteRelay15Trap, 
                            remoteRelay16Trap}
    STATUS              current
    DESCRIPTION         "Remote Output Relay group"
    ::= {envGroups 22}

	
-- hostSystem subtree

sysTime					OBJECT-TYPE
	SYNTAX				DisplayString
	MAX-ACCESS			read-only
	STATUS				current
	DESCRIPTION		    "System time"
	::= { hostSystem 1 }

sysEnterpriseName		OBJECT-TYPE
	SYNTAX				DisplayString
	MAX-ACCESS  		read-only
	STATUS				current
	DESCRIPTION		    "Enterprise Name"
	::= { hostSystem 2 }

sysEnterpriseLocation	OBJECT-TYPE
	SYNTAX				DisplayString
	MAX-ACCESS  		read-only
	STATUS				current
	DESCRIPTION		    "Enterprise Location"
	::= { hostSystem 3 }

sysEnterpriseBranch 	OBJECT-TYPE
	SYNTAX				DisplayString
	MAX-ACCESS  		read-only
	STATUS				current
	DESCRIPTION		    "Enterprise Branch"
	::= { hostSystem 4 }

sysEnterpriseRack	OBJECT-TYPE
	SYNTAX				DisplayString
	MAX-ACCESS  		read-only
	STATUS				current
	DESCRIPTION		    "Enterprise Rack"
	::= { hostSystem 5 }

sysEnterpriseContact	OBJECT-TYPE
	SYNTAX				DisplayString
	MAX-ACCESS  		read-only
	STATUS				current
	DESCRIPTION		    "Enterprise Contact"
	::= { hostSystem 6 }

sysEnterprisePhone  	OBJECT-TYPE
	SYNTAX				DisplayString
	MAX-ACCESS  		read-only
	STATUS				current
	DESCRIPTION		    "Enterprise Phone"
	::= { hostSystem 7 }

firmwareVersion  		OBJECT-TYPE
	SYNTAX				DisplayString
	MAX-ACCESS  		read-only
	STATUS				current
	DESCRIPTION		    "Firmware Version"
	::= { hostSystem 8 }

deviceModel  			OBJECT-TYPE
	SYNTAX				DisplayString
	MAX-ACCESS  		read-only
	STATUS				current
	DESCRIPTION		    "Device Model"
	::= { hostSystem 9 }

sysReset				OBJECT-TYPE
	SYNTAX				INTEGER {normal(0), reboot(1)}
	MAX-ACCESS			read-write
	STATUS				current
	DESCRIPTION		    "Initiates system reboot. Normal value: 0, set 1 to reboot"
	::= { hostSystem 10 }

devSerialNum 			OBJECT-TYPE
	SYNTAX				DisplayString		
	MAX-ACCESS			read-only
	STATUS				current
	DESCRIPTION		    "Serial Number"
	::= { hostSystem 11 }

devHardwareRev			OBJECT-TYPE
	SYNTAX				DisplayString		
	MAX-ACCESS			read-only
	STATUS				current
	DESCRIPTION		    "Hardware Revision"
	::= { hostSystem 12 }

devManufacturer			OBJECT-TYPE
	SYNTAX				DisplayString		
	MAX-ACCESS			read-only
	STATUS				current
	DESCRIPTION		    "Device Manufacturer"
	::= { hostSystem 13 }

-- internal sensors description

intSensorTable			OBJECT-TYPE
	SYNTAX	            SEQUENCE OF	IntSensorEntry
	MAX-ACCESS          not-accessible
	STATUS	            current
	DESCRIPTION         "Table of internal Sensors entries"
	::= { intSensors 1 }

intSensorEntry     		OBJECT-TYPE
    SYNTAX              IntSensorEntry
	MAX-ACCESS          not-accessible
	STATUS	            current
	DESCRIPTION         "An internal sensor entry"
	INDEX               { intSensorIndex }
	::= { intSensorTable 1 }

IntSensorEntry ::= 
	SEQUENCE {
		intSensorIndex
			Integer32,
		intSensorType
			INTEGER,
		intSensorDescription
			DisplayString,
		intSensorGroupNb
			Integer32,
		intSensorGroup
			DisplayString,
        intSensorValue
            INTEGER,
		intSensorUnit
			Integer32,
		intSensorUnitName
			DisplayString,
		intSensorStatus
			INTEGER,
		intSensorMinThreshold
			Integer32,
		intSensorMaxThreshold
			Integer32,
		intSensorMinWarnThreshold
			Integer32,
		intSensorMaxWarnThreshold
			Integer32
	}

intSensorIndex			OBJECT-TYPE
	SYNTAX				Integer32 (0..10000)
	MAX-ACCESS			accessible-for-notify
	STATUS				current
	DESCRIPTION	        "The index of the internal sensor entry 1..3"
	::= { intSensorEntry 1 }

intSensorType		    OBJECT-TYPE
	SYNTAX				INTEGER {  undefined(0), temperature(1), humidity(2), power(3), lowVoltage(4), current(5), aclmvVoltage(6), aclmpVoltage(7), aclmpPower(8),water(9), smoke(10), vibration(11), motion(12), glass(13), door(14), keypad(15), panicButton(16), keyStation(17), digInput(18), light(22), rmsVoltage(41), rmsCurrent(42), activePower(43), reactivePower(44), tempHum(513), custom(32767), temperatureCombo(32769), humidityCombo(32770), tempHum2(540)  }
	MAX-ACCESS  		read-only
	STATUS				current
	DESCRIPTION	        "Sensor Type"
	::= { intSensorEntry 2 }

intSensorDescription    OBJECT-TYPE
	SYNTAX				DisplayString
	MAX-ACCESS  		read-only
	STATUS				current
	DESCRIPTION	        "Sensor Description"
	::= { intSensorEntry 3 }
    
intSensorGroupNb        OBJECT-TYPE
	SYNTAX				Integer32 (1..8)
	MAX-ACCESS  		read-only
	STATUS				current
	DESCRIPTION	        "Sensor's Group"
	::= { intSensorEntry 4 }
    
intSensorGroup          OBJECT-TYPE
	SYNTAX				DisplayString
	MAX-ACCESS  		read-only
	STATUS				current
	DESCRIPTION	        "Sensor's Group Name"
	::= { intSensorEntry 5 }
    
intSensorValue			OBJECT-TYPE
	SYNTAX				INTEGER { closed(0), open(1) }
	MAX-ACCESS			read-only
	STATUS				current
	DESCRIPTION	        "The value of the internal sensor reading. For temperature, voltage, current or low voltage,  it is presented in tenths of degrees/volts"
	::= { intSensorEntry 6 }
	
intSensorUnit			OBJECT-TYPE
	SYNTAX				Integer32 (0..1)
	MAX-ACCESS			read-only
	STATUS				current
	DESCRIPTION	        "The measuremnet unit for this sensor in numeric format. It is important only for temperature"
	::= { intSensorEntry 7 }
	
intSensorUnitName   	OBJECT-TYPE
	SYNTAX				DisplayString
	MAX-ACCESS			read-only
	STATUS				current
	DESCRIPTION	        "The measuremnet unit for this sensor in readable format"
	::= { intSensorEntry 8 }
	
intSensorStatus			OBJECT-TYPE
	SYNTAX				INTEGER {notconnected(0), normal(1), prealert(2), alert(3), acknowledged(4), dismissed(5), disconnected(6) }
	MAX-ACCESS			read-write
	STATUS				current
	DESCRIPTION	        "The status of the sensor"
	::= { intSensorEntry 9 }
	
intSensorMinThreshold	OBJECT-TYPE
	SYNTAX				Integer32 (0..1000)
	MAX-ACCESS			read-write
	STATUS				current
	DESCRIPTION	        "The value of the sensor lower threshold"
	::= { intSensorEntry 10 }
	
intSensorMaxThreshold	OBJECT-TYPE
	SYNTAX				Integer32 (0..1000)
	MAX-ACCESS			read-write
	STATUS				current
	DESCRIPTION	        "The value of the sensor upper threshold"
	::= { intSensorEntry 11 }
	
intSensorMinWarnThreshold	OBJECT-TYPE
	SYNTAX				Integer32 (0..1000)
	MAX-ACCESS			read-write
	STATUS				current
	DESCRIPTION	        "The value of the sensor lower warning threshold"
	::= { intSensorEntry 12 }
	
intSensorMaxWarnThreshold	OBJECT-TYPE
	SYNTAX				Integer32 (0..1000)
	MAX-ACCESS			read-write
	STATUS				current
	DESCRIPTION	        "The value of the sensor upper warning threshold"
	::= { intSensorEntry 13 }
	
-- external auxiliary sensors description

auxSensorTable		OBJECT-TYPE
	SYNTAX	            SEQUENCE OF	AuxSensorEntry
	MAX-ACCESS          not-accessible
	STATUS	            current
	DESCRIPTION         "Table of auxiliary sensors entries"
	::= { auxSensors 1 }

auxSensorEntry		OBJECT-TYPE
    SYNTAX              AuxSensorEntry
	MAX-ACCESS          not-accessible
	STATUS	            current
	DESCRIPTION         "An auxiliary sensor entry"
	INDEX               { auxSensorIndex }
	::= { auxSensorTable 1 }

AuxSensorEntry ::= 
	SEQUENCE {
		auxSensorIndex
			Integer32,
		auxSensorType
			INTEGER,
		auxSensorDescription
			DisplayString,
		auxSensorConnector
			Integer32,
		auxSensorGroupNb
			Integer32,
		auxSensorGroup
			DisplayString,
        auxSensorValue
            INTEGER,
		auxSensorUnit
			Integer32,
		auxSensorUnitName
			DisplayString,
		auxSensorStatus
			INTEGER,
		auxSensorMinThreshold
			Integer32,
		auxSensorMaxThreshold
			Integer32,
		auxSensorMinWarnThreshold
			Integer32,
		auxSensorMaxWarnThreshold
			Integer32
	}

auxSensorIndex			OBJECT-TYPE
	SYNTAX				Integer32 (0..10000)
	MAX-ACCESS			accessible-for-notify
	STATUS				current
	DESCRIPTION	        "The index of the auxiliary sensor entry 1..2"
	::= { auxSensorEntry 1 }

auxSensorType		    OBJECT-TYPE
	SYNTAX				INTEGER {  undefined(0), dewPoint(24), frequency(35), acVoltage(36), acCurrent(37), dcVoltage(38), dcCurrent(39), rmsVoltage(41), rmsCurrent(42), activePower(43), reactivePower(44) , aldsTotalLength(47) }
	MAX-ACCESS  		read-only
	STATUS				current
	DESCRIPTION	        "Auxiliary Sensor Type"
	::= { auxSensorEntry 2 }

auxSensorDescription    OBJECT-TYPE
	SYNTAX				DisplayString
	MAX-ACCESS  		read-only
	STATUS				current
	DESCRIPTION	        "Auxiliary Sensor Description"
	::= { auxSensorEntry 3 }
    
auxSensorConnector      OBJECT-TYPE
	SYNTAX				Integer32 (1..16)
	MAX-ACCESS  		read-only
	STATUS				current
	DESCRIPTION	        "Connector where the auxiliary sensor is attached"
	::= { auxSensorEntry 4 }
    
auxSensorGroupNb        OBJECT-TYPE
	SYNTAX				Integer32 (1..8)
	MAX-ACCESS  		read-only
	STATUS				current
	DESCRIPTION	        "Auxiliary Sensor's Group"
	::= { auxSensorEntry 5 }
    
auxSensorGroup          OBJECT-TYPE
	SYNTAX				DisplayString
	MAX-ACCESS  		read-only
	STATUS				current
	DESCRIPTION	        "Auxiliary Sensor's Group Name"
	::= { auxSensorEntry 6 }
    
auxSensorValue			OBJECT-TYPE
	SYNTAX				INTEGER
	MAX-ACCESS			read-only
	STATUS				current
	DESCRIPTION	        "The value of the auxiliary sensor reading. It is presented in tenths of degrees"
	::= { auxSensorEntry 7 }
	
auxSensorUnit			OBJECT-TYPE
	SYNTAX				Integer32 (0..1)
	MAX-ACCESS			read-only
	STATUS				current
	DESCRIPTION	        "The measuremnet unit for this sensor. Can be Celsius or Fahrenheit"
	::= { auxSensorEntry 8 }
	
auxSensorUnitName   	OBJECT-TYPE
	SYNTAX				DisplayString
	MAX-ACCESS			read-only
	STATUS				current
	DESCRIPTION	        "The measuremnet unit for this sensor in readable format"
	::= { auxSensorEntry 9 }
	
auxSensorStatus			OBJECT-TYPE
	SYNTAX				INTEGER {notconnected(0), normal(1), prealert(2), alert(3), acknowledged(4), dismissed(5), disconnected(6), notApplicable(11) }
	MAX-ACCESS			read-write
	STATUS				current
	DESCRIPTION	        "The status of the auxiliary sensor"
	::= { auxSensorEntry 10 }
	
auxSensorMinThreshold	OBJECT-TYPE
	SYNTAX				Integer32 (0..1000)
	MAX-ACCESS			read-write
	STATUS				current
	DESCRIPTION	        "The value of the sensor lower threshold"
	::= { auxSensorEntry 11 }
	
auxSensorMaxThreshold	OBJECT-TYPE
	SYNTAX				Integer32 (0..1000)
	MAX-ACCESS			read-write
	STATUS				current
	DESCRIPTION	        "The value of the sensor upper threshold"
	::= { auxSensorEntry 12 }
	
auxSensorMinWarnThreshold	OBJECT-TYPE
	SYNTAX				Integer32 (0..1000)
	MAX-ACCESS			read-write
	STATUS				current
	DESCRIPTION	        "The value of the sensor lower warning threshold"
	::= { auxSensorEntry 13 }
	
auxSensorMaxWarnThreshold	OBJECT-TYPE
	SYNTAX				Integer32 (0..1000)
	MAX-ACCESS			read-write
	STATUS				current
	DESCRIPTION	        "The value of the sensor upper warning threshold"
	::= { auxSensorEntry 14 }
	

-- external auxiliary 2 sensors description

aux2SensorTable		OBJECT-TYPE
	SYNTAX	            SEQUENCE OF	Aux2SensorEntry
	MAX-ACCESS          not-accessible
	STATUS	            current
	DESCRIPTION         "Table of auxiliary sensors entries"
	::= { aux2Sensors 1 }

aux2SensorEntry		OBJECT-TYPE
    SYNTAX              Aux2SensorEntry
	MAX-ACCESS          not-accessible
	STATUS	            current
	DESCRIPTION         "An auxiliary 2 sensor entry"
	INDEX               { aux2SensorIndex }
	::= { aux2SensorTable 1 }

Aux2SensorEntry ::= 
	SEQUENCE {
		aux2SensorIndex
			Integer32,
		aux2SensorType
			INTEGER,
		aux2SensorDescription
			DisplayString,
		aux2SensorConnector
			Integer32,
		aux2SensorGroupNb
			Integer32,
		aux2SensorGroup
			DisplayString,
        aux2SensorValue
            INTEGER,
		aux2SensorUnit
			Integer32,
		aux2SensorUnitName
			DisplayString,
		aux2SensorStatus
			INTEGER,
		aux2SensorMinThreshold
			Integer32,
		aux2SensorMaxThreshold
			Integer32,
		aux2SensorMinWarnThreshold
			Integer32,
		aux2SensorMaxWarnThreshold
			Integer32
	}

aux2SensorIndex			OBJECT-TYPE
	SYNTAX				Integer32 (0..10000)
	MAX-ACCESS			accessible-for-notify
	STATUS				current
	DESCRIPTION	        "The index of the auxiliary 2 sensor entry 1..96"
	::= { aux2SensorEntry 1 }

aux2SensorType		    OBJECT-TYPE
	SYNTAX				INTEGER { undefined(0), dcVoltage(38), dcCurrent(39), rmsVoltage(41), rmsCurrent(42), activePower(43), reactivePower(44) }
	MAX-ACCESS  		read-only
	STATUS				current
	DESCRIPTION	        "Auxiliary 2 Sensor Type"
	::= { aux2SensorEntry 2 }

aux2SensorDescription    OBJECT-TYPE
	SYNTAX				DisplayString
	MAX-ACCESS  		read-only
	STATUS				current
	DESCRIPTION	        "Auxiliary 2 Sensor Description"
	::= { aux2SensorEntry 3 }
    
aux2SensorConnector      OBJECT-TYPE
	SYNTAX				Integer32 (1..16)
	MAX-ACCESS  		read-only
	STATUS				current
	DESCRIPTION	        "Connector where the auxiliary 2 sensor is attached"
	::= { aux2SensorEntry 4 }
    
aux2SensorGroupNb        OBJECT-TYPE
	SYNTAX				Integer32 (1..8)
	MAX-ACCESS  		read-only
	STATUS				current
	DESCRIPTION	        "Auxiliary 2 Sensor's Group"
	::= { aux2SensorEntry 5 }
    
aux2SensorGroup          OBJECT-TYPE
	SYNTAX				DisplayString
	MAX-ACCESS  		read-only
	STATUS				current
	DESCRIPTION	        "Auxiliary 2 Sensor's Group Name"
	::= { aux2SensorEntry 6 }
    
aux2SensorValue			OBJECT-TYPE
	SYNTAX				INTEGER
	MAX-ACCESS			read-only
	STATUS				current
	DESCRIPTION	        "The value of the auxiliary 2 sensor reading. It is presented in tenths of degrees"
	::= { aux2SensorEntry 7 }
	
aux2SensorUnit			OBJECT-TYPE
	SYNTAX				Integer32 (0..1)
	MAX-ACCESS			read-only
	STATUS				current
	DESCRIPTION	        "The measuremnet unit for this sensor. Can be Celsius or Fahrenheit"
	::= { aux2SensorEntry 8 }
	
aux2SensorUnitName   	OBJECT-TYPE
	SYNTAX				DisplayString
	MAX-ACCESS			read-only
	STATUS				current
	DESCRIPTION	        "The measuremnet unit for this sensor in readable format"
	::= { aux2SensorEntry 9 }
	
aux2SensorStatus			OBJECT-TYPE
	SYNTAX				INTEGER {notconnected(0), normal(1), prealert(2), alert(3), acknowledged(4), dismissed(5), disconnected(6) }
	MAX-ACCESS			read-write
	STATUS				current
	DESCRIPTION	        "The status of the auxiliary 2 sensor"
	::= { aux2SensorEntry 10 }
	
aux2SensorMinThreshold	OBJECT-TYPE
	SYNTAX				Integer32 (0..1000)
	MAX-ACCESS			read-write
	STATUS				current
	DESCRIPTION	        "The value of the sensor lower threshold"
	::= { aux2SensorEntry 11 }
	
aux2SensorMaxThreshold	OBJECT-TYPE
	SYNTAX				Integer32 (0..1000)
	MAX-ACCESS			read-write
	STATUS				current
	DESCRIPTION	        "The value of the sensor upper threshold"
	::= { aux2SensorEntry 12 }
	
aux2SensorMinWarnThreshold	OBJECT-TYPE
	SYNTAX				Integer32 (0..1000)
	MAX-ACCESS			read-write
	STATUS				current
	DESCRIPTION	        "The value of the sensor lower warning threshold"
	::= { aux2SensorEntry 13 }
	
aux2SensorMaxWarnThreshold	OBJECT-TYPE
	SYNTAX				Integer32 (0..1000)
	MAX-ACCESS			read-write
	STATUS				current
	DESCRIPTION	        "The value of the sensor upper warning threshold"
	::= { aux2SensorEntry 14 }
	

-- external sensors description

extSensorTable			OBJECT-TYPE
	SYNTAX	            SEQUENCE OF	ExtSensorEntry
	MAX-ACCESS          not-accessible
	STATUS	            current
	DESCRIPTION         "Table of external Sensors entries"
	::= { extSensors 1 }

extSensorEntry     		OBJECT-TYPE
    SYNTAX              ExtSensorEntry
	MAX-ACCESS          not-accessible
	STATUS	            current
	DESCRIPTION         "An external sensor entry"
	INDEX               { extSensorIndex }
	::= { extSensorTable 1 }

ExtSensorEntry ::= 
	SEQUENCE {
		extSensorIndex
			Integer32,
		extSensorType
			INTEGER,
		extSensorDescription
			DisplayString,
		extSensorConnector
			Integer32,
		extSensorGroupNb
			Integer32,
		extSensorGroup
			DisplayString,
        extSensorValue
            INTEGER,
		extSensorUnit
			Integer32,
		extSensorUnitName
			DisplayString,
		extSensorStatus
			INTEGER,
		extSensorMinThreshold
			Integer32,
		extSensorMaxThreshold
			Integer32,
		extSensorMinWarnThreshold
			Integer32,
		extSensorMaxWarnThreshold
			Integer32
	}

extSensorIndex			OBJECT-TYPE
	SYNTAX				Integer32 (0..10000)
	MAX-ACCESS			accessible-for-notify
	STATUS				current
	DESCRIPTION	        "The index of the external sensor entry 1..4"
	::= { extSensorEntry 1 }

extSensorType		    OBJECT-TYPE
	SYNTAX				INTEGER {  undefined(0), temperature(1), humidity(2), power(3), lowVoltage(4), current(5), aclmvVoltage(6), aclmpVoltage(7), aclmpPower(8),water(9), smoke(10), vibration(11), motion(12), glass(13), door(14), keypad(15), panicButton(16), keyStation(17), digInput(18), light(22), tacDio(26), rmsVoltage(41), rmsCurrent(42), activePower(43), reactivePower(44), aldsLeakLocation(45), aldsContinuity(46), tempHum(513), custom(32767), temperatureCombo(32769), humidityCombo(32770)  }
	MAX-ACCESS  		read-only
	STATUS				current
	DESCRIPTION	        "Sensor Type"
	::= { extSensorEntry 2 }

extSensorDescription    OBJECT-TYPE
	SYNTAX				DisplayString
	MAX-ACCESS  		read-only
	STATUS				current
	DESCRIPTION	        "Sensor Description"
	::= { extSensorEntry 3 }
    
extSensorConnector      OBJECT-TYPE
	SYNTAX				Integer32 (1..16)
	MAX-ACCESS  		read-only
	STATUS				current
	DESCRIPTION	        "Connector where the sensor is attached"
	::= { extSensorEntry 4 }
    
extSensorGroupNb        OBJECT-TYPE
	SYNTAX				Integer32 (1..8)
	MAX-ACCESS  		read-only
	STATUS				current
	DESCRIPTION	        "Sensor's Group"
	::= { extSensorEntry 5 }
    
extSensorGroup          OBJECT-TYPE
	SYNTAX				DisplayString
	MAX-ACCESS  		read-only
	STATUS				current
	DESCRIPTION	        "Sensor's Group Name"
	::= { extSensorEntry 6 }
    
extSensorValue			OBJECT-TYPE
	SYNTAX				INTEGER { closed(0), open(1), normal(2), break(3) }
	MAX-ACCESS			read-only
	STATUS				current
	DESCRIPTION	        "The value of the external sensor reading. For temperature, voltage, current or low voltage,  it is presented in tenths of degrees/volts"
	::= { extSensorEntry 7 }
	
extSensorUnit			OBJECT-TYPE
	SYNTAX				Integer32 (0..1)
	MAX-ACCESS			read-only
	STATUS				current
	DESCRIPTION	        "The measuremnet unit for this sensor. It is important only for temperature"
	::= { extSensorEntry 8 }
	
extSensorUnitName   	OBJECT-TYPE
	SYNTAX				DisplayString
	MAX-ACCESS			read-only
	STATUS				current
	DESCRIPTION	        "The measuremnet unit for this sensor in readable format"
	::= { extSensorEntry 9 }
	
extSensorStatus			OBJECT-TYPE
	SYNTAX				INTEGER {notconnected(0), normal(1), prealert(2), alert(3), acknowledged(4), dismissed(5), disconnected(6) }
	MAX-ACCESS			read-write
	STATUS				current
	DESCRIPTION	        "The status of the sensor"
	::= { extSensorEntry 10 }
	
extSensorMinThreshold	OBJECT-TYPE
	SYNTAX				Integer32 (0..1000)
	MAX-ACCESS			read-write
	STATUS				current
	DESCRIPTION	        "The value of the sensor lower threshold"
	::= { extSensorEntry 11 }
	
extSensorMaxThreshold	OBJECT-TYPE
	SYNTAX				Integer32 (0..1000)
	MAX-ACCESS			read-write
	STATUS				current
	DESCRIPTION	        "The value of the sensor upper threshold"
	::= { extSensorEntry 12 }
	
extSensorMinWarnThreshold	OBJECT-TYPE
	SYNTAX				Integer32 (0..1000)
	MAX-ACCESS			read-write
	STATUS				current
	DESCRIPTION	        "The value of the sensor lower warning threshold"
	::= { extSensorEntry 13 }
	
extSensorMaxWarnThreshold	OBJECT-TYPE
	SYNTAX				Integer32 (0..1000)
	MAX-ACCESS			read-write
	STATUS				current
	DESCRIPTION	        "The value of the sensor upper warning threshold"
	::= { extSensorEntry 14 }
	
extSensorAclmTable		OBJECT-TYPE
	SYNTAX	            SEQUENCE OF	ExtSensorAclmValues
	MAX-ACCESS          not-accessible
	STATUS	            current
	DESCRIPTION         "Table of external Sensors entries"
	::= { extSensors 2 }

extSensorAclmValues		OBJECT-TYPE
    SYNTAX              ExtSensorAclmValues
	MAX-ACCESS          not-accessible
	STATUS	            current
	DESCRIPTION         "An external sensor entry"
	INDEX               { extSensorAclmIndex }
	::= { extSensorAclmTable 1 }

ExtSensorAclmValues ::=
        SEQUENCE {
                extSensorAclmIndex
                        Integer32,
                extSensorPeakValue
                        Integer32,
                extSensorFrequency
                        Integer32,
                extSensorCurrent
                        Integer32,
                extSensorSpikes
                        Integer32,
                extSensorSwells
                        Integer32,
                extSensorSags
                        Integer32,
                extSensorRelay
                        INTEGER
        }

extSensorAclmIndex      OBJECT-TYPE
	SYNTAX				Integer32 (0..1000)
	MAX-ACCESS			read-only
	STATUS				current
	DESCRIPTION	        "Index of the sensor in the list"
	::= { extSensorAclmValues 1 }
        
extSensorPeakValue	    OBJECT-TYPE
	SYNTAX				Integer32 (0..1000)
	MAX-ACCESS			read-only
	STATUS				current
	DESCRIPTION	        "The peak value of the ACLM sensor presensted in tenths of volts/watts"
	::= { extSensorAclmValues 2 }
	
extSensorFrequency	    OBJECT-TYPE
	SYNTAX				Integer32 (0..1000)
	MAX-ACCESS			read-only
	STATUS				current
	DESCRIPTION	        "Frequency measured by the ACLM sensor presensted in tenths of Hz"
	::= { extSensorAclmValues 3 }
	
extSensorCurrent	    OBJECT-TYPE
	SYNTAX				Integer32 (0..1000)
	MAX-ACCESS			read-only
	STATUS				current
	DESCRIPTION	        "Current measured by the ACLM sensor presensted in tenths of A(mpers)"
	::= { extSensorAclmValues 4 }
	
extSensorSpikes	        OBJECT-TYPE
	SYNTAX				Integer32 (0..1000)
	MAX-ACCESS			read-only
	STATUS				current
	DESCRIPTION	        "Number of spikes read"
	::= { extSensorAclmValues 5 }
	
extSensorSwells	        OBJECT-TYPE
	SYNTAX				Integer32 (0..1000)
	MAX-ACCESS			read-only
	STATUS				current
	DESCRIPTION	        "Number of swells read"
	::= { extSensorAclmValues 6 }
	
extSensorSags	        OBJECT-TYPE
	SYNTAX				Integer32 (0..1000)
	MAX-ACCESS			read-only
	STATUS				current
	DESCRIPTION	        "Number of sags read"
	::= { extSensorAclmValues 7 }

extSensorRelay          OBJECT-TYPE
    SYNTAX              INTEGER { closed(0), open(1) }
	MAX-ACCESS			read-only
	STATUS				current
	DESCRIPTION	        "Relay status"
	::= { extSensorAclmValues 8 }



-- external Tac sensors description

tacSensorTable		OBJECT-TYPE
	SYNTAX	            SEQUENCE OF	TacSensorEntry
	MAX-ACCESS          not-accessible
	STATUS	            current
	DESCRIPTION         "Table of Tac sensors entries"
	::= { tacSensors 1 }

tacSensorEntry		OBJECT-TYPE
    SYNTAX              TacSensorEntry
	MAX-ACCESS          not-accessible
	STATUS	            current
	DESCRIPTION         "A tac sensor entry"
	INDEX               { tacSensorIndex }
	::= { tacSensorTable 1 }

TacSensorEntry ::= 
	SEQUENCE {
		tacSensorIndex
			Integer32,
		tacSensorType
			INTEGER,
		tacSensorDescription
			DisplayString,
        tacSensorConnector
            Integer32,
		tacSensorGroupNb
			Integer32,
		tacSensorGroup
			DisplayString,
        tacSensorValue
            Integer32,
		tacSensorUnit
			Integer32,
		tacSensorUnitName
			DisplayString,
		tacSensorStatus
			INTEGER,
		tacSensorMinThreshold
			Integer32,
		tacSensorMaxThreshold
			Integer32,
		tacSensorMinWarnThreshold
			Integer32,
		tacSensorMaxWarnThreshold
			Integer32
	}

tacSensorIndex			OBJECT-TYPE
	SYNTAX				Integer32 (0..10000)
	MAX-ACCESS			accessible-for-notify
	STATUS				current
	DESCRIPTION	        "The index of the Tac sensor entry 1..4"
	::= { tacSensorEntry 1 }

tacSensorType		    OBJECT-TYPE
	SYNTAX				INTEGER {  undefined(0), tac(29) }
	MAX-ACCESS  		read-only
	STATUS				current
	DESCRIPTION	        "Tac Sensor Type"
	::= { tacSensorEntry 2 }

tacSensorDescription    OBJECT-TYPE
	SYNTAX				DisplayString
	MAX-ACCESS  		read-only
	STATUS				current
	DESCRIPTION	        "Tac Sensor Description"
	::= { tacSensorEntry 3 }
    
tacSensorConnector      OBJECT-TYPE
	SYNTAX		        Integer32 (1..16)
	MAX-ACCESS  		read-only
	STATUS			current
	DESCRIPTION	        "Connector where the Tac sensor is attached"
	::= { tacSensorEntry 4 }
    
tacSensorGroupNb        OBJECT-TYPE
	SYNTAX				Integer32 (1..8)
	MAX-ACCESS  		read-only
	STATUS				current
	DESCRIPTION	        "Tac Sensor's Group"
	::= { tacSensorEntry 5 }
    
tacSensorGroup          OBJECT-TYPE
	SYNTAX				DisplayString
	MAX-ACCESS  		read-only
	STATUS				current
	DESCRIPTION	        "Tac Sensor's Group Name"
	::= { tacSensorEntry 6 }
    
tacSensorValue			OBJECT-TYPE
	SYNTAX				Integer32
	MAX-ACCESS			read-only
	STATUS				current
	DESCRIPTION	        "The value of the Tac sensor reading."
	::= { tacSensorEntry 7 }
	
tacSensorUnit			OBJECT-TYPE
	SYNTAX				Integer32 (0..1)
	MAX-ACCESS			read-only
	STATUS				current
	DESCRIPTION	        "The measuremnet unit for this sensor. Can be Celsius or Fahrenheit"
	::= { tacSensorEntry 8 }
	
tacSensorUnitName   	OBJECT-TYPE
	SYNTAX				DisplayString
	MAX-ACCESS			read-only
	STATUS				current
	DESCRIPTION	        "The measuremnet unit for this sensor in readable format"
	::= { tacSensorEntry 9 }
	
tacSensorStatus			OBJECT-TYPE
	SYNTAX				INTEGER {notconnected(0), normal(1), prealert(2), alert(3), acknowledged(4), dismissed(5), disconnected(6) }
	MAX-ACCESS			read-write
	STATUS				current
	DESCRIPTION	        "The status of the Tac sensor"
	::= { tacSensorEntry 10 }
	
tacSensorMinThreshold	OBJECT-TYPE
	SYNTAX				Integer32 (0..1000)
	MAX-ACCESS			read-write
	STATUS				current
	DESCRIPTION	        "The value of the sensor lower threshold"
	::= { tacSensorEntry 11 }
	
tacSensorMaxThreshold	OBJECT-TYPE
	SYNTAX				Integer32 (0..1000)
	MAX-ACCESS			read-write
	STATUS				current
	DESCRIPTION	        "The value of the sensor upper threshold"
	::= { tacSensorEntry 12 }
	
tacSensorMinWarnThreshold	OBJECT-TYPE
	SYNTAX				Integer32 (0..1000)
	MAX-ACCESS			read-write
	STATUS				current
	DESCRIPTION	        "The value of the sensor lower warning threshold"
	::= { tacSensorEntry 13 }
	
tacSensorMaxWarnThreshold	OBJECT-TYPE
	SYNTAX				Integer32 (0..1000)
	MAX-ACCESS			read-write
	STATUS				current
	DESCRIPTION	        "The value of the sensor upper warning threshold"
	::= { tacSensorEntry 14 }
	

	
-- dry contacts description

digInputTable	   	OBJECT-TYPE
	SYNTAX	            SEQUENCE OF	DryContactEntry
	MAX-ACCESS          not-accessible
	STATUS	            current
	DESCRIPTION         "Table of external Sensors entries"
	::= { digInputs 1 }

digInputEntry   		OBJECT-TYPE
    SYNTAX              DryContactEntry
	MAX-ACCESS          not-accessible
	STATUS	            current
	DESCRIPTION         "A dry contact entry"
	INDEX               { digInputIndex }
	::= { digInputTable 1 }

DryContactEntry ::= 
	SEQUENCE {
		digInputIndex
			Integer32,
		digInputType
			INTEGER,
		digInputDescription
			DisplayString,
		digInputConnector
			Integer32,
		digInputGroupNb
			Integer32,
		digInputGroup
			DisplayString,
        digInputValue
            INTEGER,
		digInputStatus
			INTEGER,
		digInputNormalValue
			INTEGER
	}

digInputIndex		OBJECT-TYPE
	SYNTAX				Integer32 (0..10000)
	MAX-ACCESS			accessible-for-notify
	STATUS				current
	DESCRIPTION	        "The index of the external sensor entry 1..4"
	::= { digInputEntry 1 }

digInputType		    OBJECT-TYPE
	SYNTAX				INTEGER { digInput(18) }
	MAX-ACCESS  		read-only
	STATUS				current
	DESCRIPTION	        "Sensor Type. Only dry contact type will be used"
	::= { digInputEntry 2 }

digInputDescription  OBJECT-TYPE
	SYNTAX				DisplayString
	MAX-ACCESS  		read-only
	STATUS				current
	DESCRIPTION	        "Sensor Description"
	::= { digInputEntry 3 }
    
digInputConnector    OBJECT-TYPE
	SYNTAX				Integer32 (1..8)
	MAX-ACCESS  		read-only
	STATUS				current
	DESCRIPTION	        "Connector where the sensor is attached"
	::= { digInputEntry 4 }
    
digInputGroupNb      OBJECT-TYPE
	SYNTAX				Integer32 (1..8)
	MAX-ACCESS  		read-only
	STATUS				current
	DESCRIPTION	        "Sensor's Group"
	::= { digInputEntry 5 }
    
digInputGroup        OBJECT-TYPE
	SYNTAX				DisplayString
	MAX-ACCESS  		read-only
	STATUS				current
	DESCRIPTION	        "Sensor's Group Name"
	::= { digInputEntry 6 }
    
digInputValue		OBJECT-TYPE
	SYNTAX				INTEGER { closed(0), open(1) }
	MAX-ACCESS			read-only
	STATUS				current
	DESCRIPTION	        "The value of the dry contact reading."
	::= { digInputEntry 7 }
	
digInputStatus		OBJECT-TYPE
	SYNTAX				INTEGER {notconnected(0), normal(1), prealert(2), alert(3), acknowledged(4), dismissed(5), disconnected(6), reserved(10) }
	MAX-ACCESS			read-write
	STATUS				current
	DESCRIPTION	        "The status of the sensor"
	::= { digInputEntry 8 }
	
digInputNormalValue  OBJECT-TYPE
	SYNTAX				INTEGER { closed(0), open(1) }
	MAX-ACCESS			read-write
	STATUS				current
	DESCRIPTION	        "The normal value of the dry contact reading"
	::= { digInputEntry 9 }
	
	
-- remote inputs description

remoteInputTable	   	OBJECT-TYPE
	SYNTAX	            SEQUENCE OF	RemoteInputEntry
	MAX-ACCESS          not-accessible
	STATUS	            current
	DESCRIPTION         "Table of Remote Inputs entries"
	::= { remoteInputs 1 }

remoteInputEntry   		OBJECT-TYPE
    SYNTAX              RemoteInputEntry
	MAX-ACCESS          not-accessible
	STATUS	            current
	DESCRIPTION         "A remote input entry"
	INDEX               { remoteInputIndex }
	::= { remoteInputTable 1 }

RemoteInputEntry ::= 
	SEQUENCE {
		remoteInputIndex
			Integer32,
		remoteInputType
			INTEGER,
		remoteInputDescription
			DisplayString,
		remoteInputConnector
			Integer32,
		remoteInputGroupNb
			Integer32,
		remoteInputGroup
			DisplayString,
        remoteInputValue
            INTEGER,
		remoteInputStatus
			INTEGER,
		remoteInputNormalValue
			INTEGER
	}

remoteInputIndex		OBJECT-TYPE
	SYNTAX				Integer32 (0..10000)
	MAX-ACCESS			accessible-for-notify
	STATUS				current
	DESCRIPTION	        "The index of the remote input entry 1..4"
	::= { remoteInputEntry 1 }

remoteInputType		    OBJECT-TYPE
	SYNTAX				INTEGER { remoteInput(18) }
	MAX-ACCESS  		read-only
	STATUS				current
	DESCRIPTION	        "Sensor Type. Remote input contact type will be used"
	::= { remoteInputEntry 2 }

remoteInputDescription  OBJECT-TYPE
	SYNTAX				DisplayString
	MAX-ACCESS  		read-only
	STATUS				current
	DESCRIPTION	        "Sensor Description"
	::= { remoteInputEntry 3 }
    
remoteInputConnector    OBJECT-TYPE
	SYNTAX				Integer32 (1..256)
	MAX-ACCESS  		read-only
	STATUS				current
	DESCRIPTION	        "Connector where the sensor is attached"
	::= { remoteInputEntry 4 }
    
remoteInputGroupNb      OBJECT-TYPE
	SYNTAX				Integer32 (1..8)
	MAX-ACCESS  		read-only
	STATUS				current
	DESCRIPTION	        "Sensor's Group"
	::= { remoteInputEntry 5 }
    
remoteInputGroup        OBJECT-TYPE
	SYNTAX				DisplayString
	MAX-ACCESS  		read-only
	STATUS				current
	DESCRIPTION	        "Sensor's Group Name"
	::= { remoteInputEntry 6 }
    
remoteInputValue		OBJECT-TYPE
	SYNTAX				INTEGER { closed(0), open(1) }
	MAX-ACCESS			read-only
	STATUS				current
	DESCRIPTION	        "The value of the remote input reading."
	::= { remoteInputEntry 7 }
	
remoteInputStatus		OBJECT-TYPE
	SYNTAX				INTEGER {notconnected(0), normal(1), prealert(2), alert(3), acknowledged(4), dismissed(5), disconnected(6) }
	MAX-ACCESS			read-write
	STATUS				current
	DESCRIPTION	        "The status of the sensor"
	::= { remoteInputEntry 8 }
	
remoteInputNormalValue  OBJECT-TYPE
	SYNTAX				INTEGER { closed(0), open(1) }
	MAX-ACCESS			read-only
	STATUS				current
	DESCRIPTION	        "The normal value of the remote input reading"
	::= { remoteInputEntry 9 }
	
	
-- IP Devices description

ipDeviceTable           OBJECT-TYPE
    SYNTAX              SEQUENCE OF IpDeviceEntry
	MAX-ACCESS          not-accessible
	STATUS	            current
	DESCRIPTION         "Table of IP Devices entries"
	::= { ipDevices 1 }

ipDeviceEntry    		OBJECT-TYPE
    SYNTAX              IpDeviceEntry
	MAX-ACCESS          not-accessible
	STATUS	            current
	DESCRIPTION         "An IP Device entry"
	INDEX               { ipDeviceIndex }
	::= { ipDeviceTable 1 }

IpDeviceEntry ::= 
	SEQUENCE {
		ipDeviceIndex
			Integer32,
		ipDeviceAddress
			DisplayString,
		ipDeviceDescription
			DisplayString,
		ipDeviceGroupNb
			Integer32,
		ipDeviceGroup
			DisplayString,
		ipDeviceTimeout
			Integer32,
		ipDeviceRetries
			Integer32,
		ipDeviceValue
			INTEGER,
		ipDeviceStatus
			INTEGER
	}

ipDeviceIndex			OBJECT-TYPE
	SYNTAX				Integer32 (0..10000)
	MAX-ACCESS			accessible-for-notify
	STATUS				current
	DESCRIPTION	        "The index of the IP Device entry 1..8"
	::= { ipDeviceEntry 1 }

ipDeviceAddress   OBJECT-TYPE
	SYNTAX				DisplayString
	MAX-ACCESS  		read-only
	STATUS				current
	DESCRIPTION	        "IP Device URL"
	::= { ipDeviceEntry 2 }
    
ipDeviceDescription     OBJECT-TYPE
	SYNTAX				DisplayString
	MAX-ACCESS  		read-only
	STATUS				current
	DESCRIPTION	        "IP Device Description"
	::= { ipDeviceEntry 3 }
    
ipDeviceGroupNb         OBJECT-TYPE
	SYNTAX				Integer32 (1..8)
	MAX-ACCESS  		read-only
	STATUS				current
	DESCRIPTION	        "Index of the group the IP Device belongs to"
	::= { ipDeviceEntry 4 }
    
ipDeviceGroup           OBJECT-TYPE
	SYNTAX				DisplayString
	MAX-ACCESS  		read-only
	STATUS				current
	DESCRIPTION	        "Name of the group the IP Device belongs to"
	::= { ipDeviceEntry 5 }
    
ipDeviceTimeout         OBJECT-TYPE
	SYNTAX				Integer32 
	MAX-ACCESS  		read-only
	STATUS				current
	DESCRIPTION	        "IP Device ping timeout (in seconds)"
	::= { ipDeviceEntry 6 }
    
ipDeviceRetries         OBJECT-TYPE
	SYNTAX				Integer32 
	MAX-ACCESS  		read-only
	STATUS				current
	DESCRIPTION	        "Number of ping retries to the IP device, until responding"
	::= { ipDeviceEntry 7 }
    
ipDeviceValue           OBJECT-TYPE
	SYNTAX				INTEGER { notResponding(0), responding(1) }
	MAX-ACCESS  		read-only
	STATUS				current
	DESCRIPTION	        "Responding status"
	::= { ipDeviceEntry 8 }
    
ipDeviceStatus          OBJECT-TYPE
	SYNTAX				INTEGER {notconnected(0), normal(1), prealert(2), alert(3), acknowledged(4), dismissed(5), disconnected(6) }
	MAX-ACCESS  		read-write
	STATUS				current
	DESCRIPTION	        "Alarm status of the IP Device"
	::= { ipDeviceEntry 9 }

-- outRelays description

outRelayTable           OBJECT-TYPE
    SYNTAX              SEQUENCE OF OutRelayEntry
    MAX-ACCESS          not-accessible
    STATUS              current
    DESCRIPTION         "Table of output relays"
    ::= { outRelays 1 }

outRelayEntry           OBJECT-TYPE
    SYNTAX              OutRelayEntry
    MAX-ACCESS          not-accessible
    STATUS              current
    DESCRIPTION         "An output relay entry"
    INDEX               { outRelayIndex }
    ::= { outRelayTable 1 }

OutRelayEntry ::=
    SEQUENCE {
        outRelayIndex
            Integer32,
        outRelayDescription
            DisplayString,            
        outRelayStatus
            INTEGER
    }

outRelayIndex           OBJECT-TYPE
    SYNTAX              Integer32 (0..10000)
    MAX-ACCESS          accessible-for-notify
    STATUS              current
    DESCRIPTION         "The index of relay"
    ::= { outRelayEntry 1 }

outRelayDescription     OBJECT-TYPE
    SYNTAX              DisplayString
    MAX-ACCESS          read-only
    STATUS              current
    DESCRIPTION         "Desciption/name associated with the output relay"
    ::= { outRelayEntry 2 }

outRelayStatus          OBJECT-TYPE
    SYNTAX              INTEGER { active(0), inactive(1) }
    MAX-ACCESS          read-write
    STATUS              current
    DESCRIPTION         "The status of the output relay"
    ::= { outRelayEntry 3 }    
    


-- remoteRelays description

remoteRelayTable           OBJECT-TYPE
    SYNTAX              SEQUENCE OF RemoteRelayEntry
    MAX-ACCESS          not-accessible
    STATUS              current
    DESCRIPTION         "Table of remote relays"
    ::= { remoteRelays 1 }

remoteRelayEntry           OBJECT-TYPE
    SYNTAX              RemoteRelayEntry
    MAX-ACCESS          not-accessible
    STATUS              current
    DESCRIPTION         "An output relay entry"
    INDEX               { remoteRelayIndex }
    ::= { remoteRelayTable 1 }

RemoteRelayEntry ::=
    SEQUENCE {
        remoteRelayIndex
            Integer32,
        remoteRelayDescription
            DisplayString,            
        remoteRelayStatus
            INTEGER
    }

remoteRelayIndex           OBJECT-TYPE
    SYNTAX              Integer32 (0..10000)
    MAX-ACCESS          accessible-for-notify
    STATUS              current
    DESCRIPTION         "The index of relay"
    ::= { remoteRelayEntry 1 }

remoteRelayDescription     OBJECT-TYPE
    SYNTAX              DisplayString
    MAX-ACCESS          read-only
    STATUS              current
    DESCRIPTION         "Desciption/name associated with the remote relay"
    ::= { remoteRelayEntry 2 }

remoteRelayStatus          OBJECT-TYPE
    SYNTAX              INTEGER { active(0), inactive(1) }
    MAX-ACCESS          read-write
    STATUS              current
    DESCRIPTION         "The status of the remote relay"
    ::= { remoteRelayEntry 3 }    
   
-- powerSupply description

pwrSupplyTable          OBJECT-TYPE
    SYNTAX              SEQUENCE OF PwrSupplyEntry
    MAX-ACCESS          not-accessible
    STATUS              current
    DESCRIPTION         "Table of power supplies"
    ::= { pwrSupplies 1 }

pwrSupplyEntry          OBJECT-TYPE
    SYNTAX              PwrSupplyEntry
    MAX-ACCESS          not-accessible
    STATUS              current
    DESCRIPTION         "An output relay entry"
    INDEX               { pwrSupplyIndex }
    ::= { pwrSupplyTable 1 }

PwrSupplyEntry ::=
    SEQUENCE {
        pwrSupplyIndex
            Integer32,
        pwrSupplyStatus
            INTEGER
    }

pwrSupplyIndex          OBJECT-TYPE
    SYNTAX              Integer32 (0..10000)
    MAX-ACCESS          accessible-for-notify
    STATUS              current
    DESCRIPTION         "The index of power supply"
    ::= { pwrSupplyEntry 1 }

pwrSupplyStatus          OBJECT-TYPE
    SYNTAX              INTEGER { failed(0), ok(1), na(2) }
    MAX-ACCESS          read-write
    STATUS              current
    DESCRIPTION         "The status of the output relay"
    ::= { pwrSupplyEntry 2 }    

-- events description

eventTable              OBJECT-TYPE
    SYNTAX              SEQUENCE OF EventEntry
    MAX-ACCESS          not-accessible
    STATUS              current
    DESCRIPTION         "Table of events"
    ::= { events 1 }

eventEntry              OBJECT-TYPE
    SYNTAX              EventEntry
    MAX-ACCESS          not-accessible
    STATUS              current
    DESCRIPTION         "An event entry"
    INDEX               { eventIndex }
    ::= { eventTable 1 }

EventEntry ::=
    SEQUENCE {
        eventIndex
            Integer32,
        eventDescription
            DisplayString,
        eventStatus
            INTEGER
    }

eventIndex              OBJECT-TYPE
    SYNTAX              Integer32 (0..10000)
    MAX-ACCESS          accessible-for-notify
    STATUS              current
    DESCRIPTION         "The index of the event"
    ::= { eventEntry 1 }

eventDescription        OBJECT-TYPE
    SYNTAX              DisplayString
    MAX-ACCESS          read-only
    STATUS              current
    DESCRIPTION         "Desciption/name associated with the event"
    ::= { eventEntry 2 }

eventStatus             OBJECT-TYPE
    SYNTAX              INTEGER { normal(1), alert(3), acknowledged(4), dismissed(5) }
    MAX-ACCESS          read-write
    STATUS              current
    DESCRIPTION         "The status of the event"
    ::= { eventEntry 3 }    

-- smartAlerts description

smartAlertTable         OBJECT-TYPE
    SYNTAX              SEQUENCE OF SmartAlertEntry
    MAX-ACCESS          not-accessible
    STATUS              current
    DESCRIPTION         "Table of smartAlerts"
    ::= { smartAlerts 1 }

smartAlertEntry         OBJECT-TYPE
    SYNTAX              SmartAlertEntry
    MAX-ACCESS          not-accessible
    STATUS              current
    DESCRIPTION         "A smartAlert entry"
    INDEX               { smartAlertIndex }
    ::= { smartAlertTable 1 }

SmartAlertEntry ::=
    SEQUENCE {
        smartAlertIndex
            Integer32,
        smartAlertDescription
            DisplayString,
        smartAlertStatus
            INTEGER
    }

smartAlertIndex         OBJECT-TYPE
    SYNTAX              Integer32 (0..10000)
    MAX-ACCESS          accessible-for-notify
    STATUS              current
    DESCRIPTION         "The index of the smartAlert"
    ::= { smartAlertEntry 1 }

smartAlertDescription   OBJECT-TYPE
    SYNTAX              DisplayString
    MAX-ACCESS          read-only
    STATUS              current
    DESCRIPTION         "Desciption/name associated with the smartAlert"
    ::= { smartAlertEntry 2 }

smartAlertStatus        OBJECT-TYPE
    SYNTAX              INTEGER { normal(1), alert(3), acknowledged(4), dismissed(5) }
    MAX-ACCESS          read-write
    STATUS              current
    DESCRIPTION         "The status of the smartAlert"
    ::= { smartAlertEntry 3 }    

-- smoke detectors description

smokeDetectorTable   	OBJECT-TYPE
	SYNTAX	            SEQUENCE OF	SmokeDetectorEntry
	MAX-ACCESS          not-accessible
	STATUS	            current
	DESCRIPTION         "Table of Smoke Detectors entries"
	::= { smokeDetectors 1 }

smokeDetectorEntry 		OBJECT-TYPE
    SYNTAX              SmokeDetectorEntry
	MAX-ACCESS          not-accessible
	STATUS	            current
	DESCRIPTION         "A smoke detector entry"
	INDEX               { smokeDetectorIndex }
	::= { smokeDetectorTable 1 }

SmokeDetectorEntry ::=
    SEQUENCE {
        smokeDetectorIndex
            Integer32,
        smokeDetectorDescription
            DisplayString,
		smokeDetectorGroupNb
			Integer32,
        smokeDetectorValue
            INTEGER,
		smokeDetectorStatus
			INTEGER
    }

smokeDetectorIndex		OBJECT-TYPE
	SYNTAX				Integer32 (0..10000)
	MAX-ACCESS			accessible-for-notify
	STATUS				current
	DESCRIPTION	        "The index of the smoke detector entry 1..8"
	::= { smokeDetectorEntry 1 }

smokeDetectorDescription    OBJECT-TYPE
	SYNTAX				DisplayString
	MAX-ACCESS  		read-only
	STATUS				current
	DESCRIPTION	        "Smoke Detector Description"
	::= { smokeDetectorEntry 2 }

smokeDetectorGroupNb    OBJECT-TYPE
	SYNTAX				Integer32 (1..8)
	MAX-ACCESS  		read-only
	STATUS				current
	DESCRIPTION	        "Sensor's Group"
	::= { smokeDetectorEntry 3 }
    
smokeDetectorValue   	OBJECT-TYPE
	SYNTAX				INTEGER { firePreAlert(0), preAlert(1), fire(2), ok(3), firePreAlertFault(4), preAlertFault(5), fireFault(6), fault(7) }
	MAX-ACCESS			read-only
	STATUS				current
	DESCRIPTION	        "The value of the smoke detector reading."
	::= { smokeDetectorEntry 4 }
	
smokeDetectorStatus		OBJECT-TYPE
	SYNTAX				INTEGER {notconnected(0), normal(1), prealert(2), alert(3), acknowledged(4), dismissed(5), disconnected(6) }
	MAX-ACCESS			read-write
	STATUS				current
	DESCRIPTION	        "The status of the smoke detector"
	::= { smokeDetectorEntry 5 }
	
-- IP Sensors    

ipSensorTable           OBJECT-TYPE
    SYNTAX              SEQUENCE OF IpSensorEntry
    MAX-ACCESS          not-accessible
    STATUS              current
    DESCRIPTION         "Table of IP Sensors entries"
    ::= { ipSensors 1 }

ipSensorEntry           OBJECT-TYPE
    SYNTAX              IpSensorEntry
    MAX-ACCESS          not-accessible
    STATUS              current
    DESCRIPTION         "An IP sensor entry"
    INDEX               { ipSensorIndex }
    ::= { ipSensorTable 1 }

IpSensorEntry ::=
    SEQUENCE {
		ipSensorIndex
			Integer32,
		ipSensorMicroUnit
			Integer32,
		ipSensorType
			INTEGER,
		ipSensorDescription
			DisplayString,
		ipSensorConnector
			Integer32,
		ipSensorGroupNb
			Integer32,
		ipSensorGroup
			DisplayString,
        ipSensorValue
            INTEGER,
		ipSensorUnit
			Integer32,
		ipSensorUnitName
			DisplayString,
		ipSensorStatus
			INTEGER,
		ipSensorMinThreshold
			Integer32,
		ipSensorMaxThreshold
			Integer32
    }

ipSensorIndex			OBJECT-TYPE
	SYNTAX				Integer32 (0..10000)
	MAX-ACCESS			accessible-for-notify
	STATUS				current
	DESCRIPTION	        "The index of the external sensor entry 1..88"
	::= { ipSensorEntry 1 }

ipSensorMicroUnit	    OBJECT-TYPE
	SYNTAX				Integer32 
	MAX-ACCESS			accessible-for-notify
	STATUS				current
	DESCRIPTION	        "The index of the Enviromux-Micro unit the sensor belongs to (1..8)"
	::= { ipSensorEntry 2 }

ipSensorType		    OBJECT-TYPE
	SYNTAX				INTEGER {  undefined(0), temperature(1), humidity(2), power(3), lowVoltage(4), current(5), aclmvVoltage(6), aclmpVoltage(7), aclmpPower(8),water(9), smoke(10), vibration(11), motion(12), glass(13), door(14), keypad(15), panicButton(16), keyStation(17), digInput(18), light(22), tacDio(26), tempHum(513), custom(32767), temperatureCombo(32769), humidityCombo(32770)  }
	MAX-ACCESS  		read-only
	STATUS				current
	DESCRIPTION	        "Sensor Type"
	::= { ipSensorEntry 3 }

ipSensorDescription    OBJECT-TYPE
	SYNTAX				DisplayString
	MAX-ACCESS  		read-only
	STATUS				current
	DESCRIPTION	        "Sensor Description"
	::= { ipSensorEntry 4 }
    
ipSensorConnector      OBJECT-TYPE
	SYNTAX				Integer32 (1..16)
	MAX-ACCESS  		read-only
	STATUS				current
	DESCRIPTION	        "Connector where the sensor is attached on the Enviromux-Micro unit, -1 if internal"
	::= { ipSensorEntry 5 }
    
ipSensorGroupNb        OBJECT-TYPE
	SYNTAX				Integer32 (1..8)
	MAX-ACCESS  		read-only
	STATUS				current
	DESCRIPTION	        "Sensor's Group"
	::= { ipSensorEntry 6 }
    
ipSensorGroup          OBJECT-TYPE
	SYNTAX				DisplayString
	MAX-ACCESS  		read-only
	STATUS				current
	DESCRIPTION	        "Sensor's Group Name"
	::= { ipSensorEntry 7 }
    
ipSensorValue			OBJECT-TYPE
	SYNTAX				INTEGER { closed(0), open(1) }
	MAX-ACCESS			read-only
	STATUS				current
	DESCRIPTION	        "The value of the external sensor reading. For temperature, voltage, current or low voltage,  it is presented in tenths of degrees/volts"
	::= { ipSensorEntry 8 }
	
ipSensorUnit			OBJECT-TYPE
	SYNTAX				Integer32 (0..1)
	MAX-ACCESS			read-only
	STATUS				current
	DESCRIPTION	        "The measuremnet unit for this sensor. It is important only for temperature"
	::= { ipSensorEntry 9 }
	
ipSensorUnitName   	OBJECT-TYPE
	SYNTAX				DisplayString
	MAX-ACCESS			read-only
	STATUS				current
	DESCRIPTION	        "The measuremnet unit for this sensor in readable format"
	::= { ipSensorEntry 10 }
	
ipSensorStatus			OBJECT-TYPE
	SYNTAX				INTEGER {notconnected(0), normal(1), prealert(2), alert(3), acknowledged(4), dismissed(5), disconnected(6) }
	MAX-ACCESS			read-write
	STATUS				current
	DESCRIPTION	        "The status of the sensor"
	::= { ipSensorEntry 11 }
	
ipSensorMinThreshold	OBJECT-TYPE
	SYNTAX				Integer32 (0..1000)
	MAX-ACCESS			read-only
	STATUS				current
	DESCRIPTION	        "The value of the sensor lower threshold"
	::= { ipSensorEntry 12 }
	
ipSensorMaxThreshold	OBJECT-TYPE
	SYNTAX				Integer32 (0..1000)
	MAX-ACCESS			read-only
	STATUS				current
	DESCRIPTION	        "The value of the sensor upper threshold"
	::= { ipSensorEntry 13 }

-- Message Registers description

msgRegistersTable       OBJECT-TYPE
    SYNTAX              SEQUENCE OF MsgRegistersEntry
    MAX-ACCESS          not-accessible
    STATUS              current
    DESCRIPTION         "Table of message registers"
    ::= { msgRegisters 1 }

msgRegistersEntry       OBJECT-TYPE
    SYNTAX              MsgRegistersEntry
    MAX-ACCESS          not-accessible
    STATUS              current
    DESCRIPTION         "An input message entry"
    INDEX               { msgRegistersIndex }
    ::= { msgRegistersTable 1 }

MsgRegistersEntry ::=
    SEQUENCE {
        msgRegistersIndex
            Integer32,
		msgRegistersDescription
			DisplayString,
        msgRegistersStatus
            INTEGER
    }

msgRegistersIndex        OBJECT-TYPE
    SYNTAX              Integer32 (1..1)
    MAX-ACCESS          read-only
    STATUS              current
    DESCRIPTION         "The index of message register"
    ::= { msgRegistersEntry 1 }

msgRegistersDescription OBJECT-TYPE
    SYNTAX              DisplayString
    MAX-ACCESS          read-write
    STATUS              current
    DESCRIPTION         "The content of the message"
    ::= { msgRegistersEntry 2 }

msgRegistersStatus      OBJECT-TYPE
    SYNTAX              INTEGER { free(0), busy(1)}
	MAX-ACCESS          read-only
    STATUS              current
    DESCRIPTION         "The status of the message register"
    ::= { msgRegistersEntry 3 }    

--Network Configure

netConfIPv4Mode  	OBJECT-TYPE
	SYNTAX				INTEGER {dhcp(0), static(1)}
	MAX-ACCESS  		read-write
	STATUS				current
	DESCRIPTION		    "Method of acquiring IP settings"
	::= { netConfRegisters 1 }

netConfIPv4Addr  	OBJECT-TYPE
	SYNTAX				DisplayString
	MAX-ACCESS  		read-write
	STATUS				current
	DESCRIPTION		    "Statically assigned IPv4 address"
	::= { netConfRegisters 2 }


netConfIPv4Mask      OBJECT-TYPE
	SYNTAX				DisplayString
	MAX-ACCESS  		read-write
	STATUS				current
	DESCRIPTION		    "Statically assigned IPv4 subnet mask"
	::= { netConfRegisters 3 }


netConfIPv4Gateway   OBJECT-TYPE
	SYNTAX				DisplayString
	MAX-ACCESS  		read-write
	STATUS				current
	DESCRIPTION		    "Statically assigned IPv4 default gateway"
	::= { netConfRegisters 4 }


netConfPreDNS        OBJECT-TYPE
	SYNTAX				DisplayString
	MAX-ACCESS  		read-write
	STATUS				current
	DESCRIPTION		    "Preferred DNS server"
	::= { netConfRegisters 5 }

netConfAltDNS        OBJECT-TYPE
	SYNTAX				DisplayString
	MAX-ACCESS  		read-write
	STATUS				current
	DESCRIPTION		    "Alternate DNS server"
	::= { netConfRegisters 6 }

netConfDNSTimeout  	OBJECT-TYPE
	SYNTAX				Integer32
	MAX-ACCESS  		read-write
	STATUS				current
	DESCRIPTION		    "Timeout for DNS request in sec"
	::= { netConfRegisters 7}

netConfIPv6Mode  	OBJECT-TYPE
	SYNTAX				INTEGER { autoconf(0), dhcp(1), static(2), disabled(3)}
	MAX-ACCESS  		read-write
	STATUS				current
	DESCRIPTION		    "Method of acquiring IPv6 settings"
	::= { netConfRegisters 8 }


netConfIPv6Addr        OBJECT-TYPE
	SYNTAX				DisplayString
	MAX-ACCESS  		read-write
	STATUS				current
	DESCRIPTION		    "IPv6 Address"
	::= { netConfRegisters 9 }


netConfIPv6Gateway        OBJECT-TYPE
	SYNTAX				DisplayString
	MAX-ACCESS  		read-write
	STATUS				current
	DESCRIPTION		    "IPv6 Default Gateway"
	::= { netConfRegisters 10 }


netConfEnable6to4Tunnel  	OBJECT-TYPE
	SYNTAX				INTEGER { disabled(0), enabled(1)}
	MAX-ACCESS  		read-write
	STATUS				current
	DESCRIPTION		    "Enable ipv6 to ipv4 Tunneling"
	::= { netConfRegisters 11 }

netConfLocalIPAddr        OBJECT-TYPE
	SYNTAX				DisplayString
	MAX-ACCESS  		read-write
	STATUS				current
	DESCRIPTION		    "IPv4 Address of local interface for 6to4 tunnel"
	::= { netConfRegisters 12 }


netConfRemoteIPv4Addr    OBJECT-TYPE
	SYNTAX					DisplayString
	MAX-ACCESS  			read-write
	STATUS					current
	DESCRIPTION				"IPv4 Address of Remote interface for 6to4 tunnel"
	::= { netConfRegisters 13 }


netConfVlanEnabled  	OBJECT-TYPE
	SYNTAX				INTEGER { disabled(0), enabled(1)}
	MAX-ACCESS  		read-write
	STATUS				current
	DESCRIPTION		    "Enable 802.1Q VLAN. Warning: Disables Regular LAN"
	::= { netConfRegisters 14 }

netConfVlanID  		OBJECT-TYPE
	SYNTAX				Integer32
	MAX-ACCESS  		read-write
	STATUS				current
	DESCRIPTION		    "VLAN ID of Tagged Packets (0-4095)"
	::= { netConfRegisters 15}

netConfSave			OBJECT-TYPE
	SYNTAX				INTEGER { normal(0), save(1)}
	MAX-ACCESS  		read-write
	STATUS				current
	DESCRIPTION		    "To Save Network Parameters: Must be set if there is any change of parameters"
	::= { netConfRegisters 16 }

netConfEnableSecurity	OBJECT-TYPE
	SYNTAX				INTEGER { disable(0), enable(1)}
	MAX-ACCESS  		read-write
	STATUS				current
	DESCRIPTION		    "Enable Network Security"
	::= { netConfRegisters 17 }

-- Trap Definitions
intSensorsTraps         OBJECT IDENTIFIER ::= { envTraps 3 }
auxSensorsTraps         OBJECT IDENTIFIER ::= { envTraps 4 }
extSensorsTraps         OBJECT IDENTIFIER ::= { envTraps 5 }
digInputsTraps          OBJECT IDENTIFIER ::= { envTraps 6 }
ipDevicesTraps          OBJECT IDENTIFIER ::= { envTraps 7 }
outRelaysTraps          OBJECT IDENTIFIER ::= { envTraps 8 }
remoteInputsTraps       OBJECT IDENTIFIER ::= { envTraps 12 }
remoteRelaysTraps       OBJECT IDENTIFIER ::= { envTraps 13 }
smokeDetectorsTraps     OBJECT IDENTIFIER ::= { envTraps 14 }
aux2SensorsTraps        OBJECT IDENTIFIER ::= { envTraps 17 }

envTrapDescription      OBJECT-TYPE
	SYNTAX				DisplayString
	MAX-ACCESS  		read-only
	STATUS				current
	DESCRIPTION	        "Message issued together with the trap to explain the reason the trap was sent"
	::= { envTraps 100 }

envTrapValue            OBJECT-TYPE
	SYNTAX				Integer32 (-1000..1000)
	MAX-ACCESS  		read-only
	STATUS				current
	DESCRIPTION	        "Message issued together with the trap to retrieve a value"
	::= { envTraps 101 }

-- sensor traps
    
-- Internal sensors traps
    
intSensor1Trap          NOTIFICATION-TYPE
    OBJECTS             { envTrapDescription, intSensorIndex, intSensorDescription, intSensorValue, intSensorUnitName, intSensorStatus }
    STATUS              current
    DESCRIPTION         "Trap issued when internal sensor 1 has a notification to send"
    ::= {intSensorsTraps 0 1 }


-- External sensors traps
    
extSensor1Trap          NOTIFICATION-TYPE
    OBJECTS             { envTrapDescription, extSensorIndex, extSensorDescription, extSensorValue, extSensorUnitName, extSensorStatus }
    STATUS              current
    DESCRIPTION         "Trap issued when external sensor 1 (Connector #1) has a notification to send"
    ::= {extSensorsTraps 0 1 }

extSensor2Trap          NOTIFICATION-TYPE
    OBJECTS             { envTrapDescription, extSensorIndex, extSensorDescription, extSensorValue, extSensorUnitName, extSensorStatus }
    STATUS              current
    DESCRIPTION         "Trap issued when external sensor 2 (Connector #1) has a notification to send"
    ::= {extSensorsTraps 0 2 }

extSensor3Trap          NOTIFICATION-TYPE
    OBJECTS             { envTrapDescription, extSensorIndex, extSensorDescription, extSensorValue, extSensorUnitName, extSensorStatus }
    STATUS              current
    DESCRIPTION         "Trap issued when external sensor 3 (Connector #2) has a notification to send"
    ::= {extSensorsTraps 0 3 }

extSensor4Trap          NOTIFICATION-TYPE
    OBJECTS             { envTrapDescription, extSensorIndex, extSensorDescription, extSensorValue, extSensorUnitName, extSensorStatus }
    STATUS              current
    DESCRIPTION         "Trap issued when external sensor 4 (Connector #2) has a notification to send"
    ::= {extSensorsTraps 0 4 }


-- Dry contacts traps
    
digInput1Trap         NOTIFICATION-TYPE
    OBJECTS             { envTrapDescription, digInputIndex, digInputDescription, digInputValue, digInputStatus }
    STATUS              current
    DESCRIPTION         "Trap issued when dry contact 1 (Connector #1) has a notification to send"
    ::= {digInputsTraps 0 1 }

digInput2Trap         NOTIFICATION-TYPE
    OBJECTS             { envTrapDescription, digInputIndex, digInputDescription, digInputValue, digInputStatus }
    STATUS              current
    DESCRIPTION         "Trap issued when dry contact 2 (Connector #2) has a notification to send"
    ::= {digInputsTraps 0 2 }

digInput3Trap         NOTIFICATION-TYPE
    OBJECTS             { envTrapDescription, digInputIndex, digInputDescription, digInputValue, digInputStatus }
    STATUS              current
    DESCRIPTION         "Trap issued when dry contact 3 (Connector #3) has a notification to send"
    ::= {digInputsTraps 0 3 }

digInput4Trap         NOTIFICATION-TYPE
    OBJECTS             { envTrapDescription, digInputIndex, digInputDescription, digInputValue, digInputStatus }
    STATUS              current
    DESCRIPTION         "Trap issued when dry contact 4 (Connector #4) has a notification to send"
    ::= {digInputsTraps 0 4 }

digInput5Trap         NOTIFICATION-TYPE
    OBJECTS             { envTrapDescription, digInputIndex, digInputDescription, digInputValue, digInputStatus }
    STATUS              current
    DESCRIPTION         "Trap issued when dry contact 5 (Connector #5) has a notification to send"
    ::= {digInputsTraps 0 5 }

-- IP Devices traps

ipDevice1Trap           NOTIFICATION-TYPE    
    OBJECTS             { envTrapDescription, ipDeviceIndex, ipDeviceAddress, ipDeviceDescription, ipDeviceValue, ipDeviceStatus }
    STATUS              current
    DESCRIPTION         "Trap issued when IP device #1 has a notification to send"
    ::= { ipDevicesTraps 0 1 }

ipDevice2Trap           NOTIFICATION-TYPE    
    OBJECTS             { envTrapDescription, ipDeviceIndex, ipDeviceAddress, ipDeviceDescription, ipDeviceValue, ipDeviceStatus }
    STATUS              current
    DESCRIPTION         "Trap issued when IP device #2 has a notification to send"
    ::= { ipDevicesTraps 0 2 }

ipDevice3Trap           NOTIFICATION-TYPE    
    OBJECTS             { envTrapDescription, ipDeviceIndex, ipDeviceAddress, ipDeviceDescription, ipDeviceValue, ipDeviceStatus }
    STATUS              current
    DESCRIPTION         "Trap issued when IP device #3 has a notification to send"
    ::= { ipDevicesTraps 0 3 }

ipDevice4Trap           NOTIFICATION-TYPE    
    OBJECTS             { envTrapDescription, ipDeviceIndex, ipDeviceAddress, ipDeviceDescription, ipDeviceValue, ipDeviceStatus }
    STATUS              current
    DESCRIPTION         "Trap issued when IP device #4 has a notification to send"
    ::= { ipDevicesTraps 0 4 }

ipDevice5Trap           NOTIFICATION-TYPE    
    OBJECTS             { envTrapDescription, ipDeviceIndex, ipDeviceAddress, ipDeviceDescription, ipDeviceValue, ipDeviceStatus }
    STATUS              current
    DESCRIPTION         "Trap issued when IP device #5 has a notification to send"
    ::= { ipDevicesTraps 0 5 }

ipDevice6Trap           NOTIFICATION-TYPE    
    OBJECTS             { envTrapDescription, ipDeviceIndex, ipDeviceAddress, ipDeviceDescription, ipDeviceValue, ipDeviceStatus }
    STATUS              current
    DESCRIPTION         "Trap issued when IP device #6 has a notification to send"
    ::= { ipDevicesTraps 0 6 }

ipDevice7Trap           NOTIFICATION-TYPE    
    OBJECTS             { envTrapDescription, ipDeviceIndex, ipDeviceAddress, ipDeviceDescription, ipDeviceValue, ipDeviceStatus }
    STATUS              current
    DESCRIPTION         "Trap issued when IP device #7 has a notification to send"
    ::= { ipDevicesTraps 0 7 }

ipDevice8Trap           NOTIFICATION-TYPE    
    OBJECTS             { envTrapDescription, ipDeviceIndex, ipDeviceAddress, ipDeviceDescription, ipDeviceValue, ipDeviceStatus }
    STATUS              current
    DESCRIPTION         "Trap issued when IP device #8 has a notification to send"
    ::= { ipDevicesTraps 0 8 }

ipDevice9Trap           NOTIFICATION-TYPE    
    OBJECTS             { envTrapDescription, ipDeviceIndex, ipDeviceAddress, ipDeviceDescription, ipDeviceValue, ipDeviceStatus }
    STATUS              current
    DESCRIPTION         "Trap issued when IP device #9 has a notification to send"
    ::= { ipDevicesTraps 0 9 }

ipDevice10Trap          NOTIFICATION-TYPE    
    OBJECTS             { envTrapDescription, ipDeviceIndex, ipDeviceAddress, ipDeviceDescription, ipDeviceValue, ipDeviceStatus }
    STATUS              current
    DESCRIPTION         "Trap issued when IP device #10 has a notification to send"
    ::= { ipDevicesTraps 0 10 }

ipDevice11Trap          NOTIFICATION-TYPE    
    OBJECTS             { envTrapDescription, ipDeviceIndex, ipDeviceAddress, ipDeviceDescription, ipDeviceValue, ipDeviceStatus }
    STATUS              current
    DESCRIPTION         "Trap issued when IP device #11 has a notification to send"
    ::= { ipDevicesTraps 0 11 }

ipDevice12Trap          NOTIFICATION-TYPE    
    OBJECTS             { envTrapDescription, ipDeviceIndex, ipDeviceAddress, ipDeviceDescription, ipDeviceValue, ipDeviceStatus }
    STATUS              current
    DESCRIPTION         "Trap issued when IP device #12 has a notification to send"
    ::= { ipDevicesTraps 0 12 }

ipDevice13Trap          NOTIFICATION-TYPE    
    OBJECTS             { envTrapDescription, ipDeviceIndex, ipDeviceAddress, ipDeviceDescription, ipDeviceValue, ipDeviceStatus }
    STATUS              current
    DESCRIPTION         "Trap issued when IP device #13 has a notification to send"
    ::= { ipDevicesTraps 0 13 }

ipDevice14Trap          NOTIFICATION-TYPE    
    OBJECTS             { envTrapDescription, ipDeviceIndex, ipDeviceAddress, ipDeviceDescription, ipDeviceValue, ipDeviceStatus }
    STATUS              current
    DESCRIPTION         "Trap issued when IP device #14 has a notification to send"
    ::= { ipDevicesTraps 0 14 }

ipDevice15Trap          NOTIFICATION-TYPE    
    OBJECTS             { envTrapDescription, ipDeviceIndex, ipDeviceAddress, ipDeviceDescription, ipDeviceValue, ipDeviceStatus }
    STATUS              current
    DESCRIPTION         "Trap issued when IP device #15 has a notification to send"
    ::= { ipDevicesTraps 0 15 }

ipDevice16Trap          NOTIFICATION-TYPE    
    OBJECTS             { envTrapDescription, ipDeviceIndex, ipDeviceAddress, ipDeviceDescription, ipDeviceValue, ipDeviceStatus }
    STATUS              current
    DESCRIPTION         "Trap issued when IP device #16 has a notification to send"
    ::= { ipDevicesTraps 0 16 }

ipDevice17Trap           NOTIFICATION-TYPE    
    OBJECTS             { envTrapDescription, ipDeviceIndex, ipDeviceAddress, ipDeviceDescription, ipDeviceValue, ipDeviceStatus }
    STATUS              current
    DESCRIPTION         "Trap issued when IP device #17 has a notification to send"
    ::= { ipDevicesTraps 0 17 }

ipDevice18Trap           NOTIFICATION-TYPE    
    OBJECTS             { envTrapDescription, ipDeviceIndex, ipDeviceAddress, ipDeviceDescription, ipDeviceValue, ipDeviceStatus }
    STATUS              current
    DESCRIPTION         "Trap issued when IP device #18 has a notification to send"
    ::= { ipDevicesTraps 0 18 }

ipDevice19Trap           NOTIFICATION-TYPE    
    OBJECTS             { envTrapDescription, ipDeviceIndex, ipDeviceAddress, ipDeviceDescription, ipDeviceValue, ipDeviceStatus }
    STATUS              current
    DESCRIPTION         "Trap issued when IP device #19 has a notification to send"
    ::= { ipDevicesTraps 0 19 }

ipDevice20Trap           NOTIFICATION-TYPE    
    OBJECTS             { envTrapDescription, ipDeviceIndex, ipDeviceAddress, ipDeviceDescription, ipDeviceValue, ipDeviceStatus }
    STATUS              current
    DESCRIPTION         "Trap issued when IP device #20 has a notification to send"
    ::= { ipDevicesTraps 0 20 }

ipDevice21Trap           NOTIFICATION-TYPE    
    OBJECTS             { envTrapDescription, ipDeviceIndex, ipDeviceAddress, ipDeviceDescription, ipDeviceValue, ipDeviceStatus }
    STATUS              current
    DESCRIPTION         "Trap issued when IP device #21 has a notification to send"
    ::= { ipDevicesTraps 0 21 }

ipDevice22Trap           NOTIFICATION-TYPE    
    OBJECTS             { envTrapDescription, ipDeviceIndex, ipDeviceAddress, ipDeviceDescription, ipDeviceValue, ipDeviceStatus }
    STATUS              current
    DESCRIPTION         "Trap issued when IP device #22 has a notification to send"
    ::= { ipDevicesTraps 0 22 }

ipDevice23Trap           NOTIFICATION-TYPE    
    OBJECTS             { envTrapDescription, ipDeviceIndex, ipDeviceAddress, ipDeviceDescription, ipDeviceValue, ipDeviceStatus }
    STATUS              current
    DESCRIPTION         "Trap issued when IP device #23 has a notification to send"
    ::= { ipDevicesTraps 0 23 }

ipDevice24Trap           NOTIFICATION-TYPE    
    OBJECTS             { envTrapDescription, ipDeviceIndex, ipDeviceAddress, ipDeviceDescription, ipDeviceValue, ipDeviceStatus }
    STATUS              current
    DESCRIPTION         "Trap issued when IP device #24 has a notification to send"
    ::= { ipDevicesTraps 0 24 }

ipDevice25Trap           NOTIFICATION-TYPE    
    OBJECTS             { envTrapDescription, ipDeviceIndex, ipDeviceAddress, ipDeviceDescription, ipDeviceValue, ipDeviceStatus }
    STATUS              current
    DESCRIPTION         "Trap issued when IP device #25 has a notification to send"
    ::= { ipDevicesTraps 0 25 }

ipDevice26Trap          NOTIFICATION-TYPE    
    OBJECTS             { envTrapDescription, ipDeviceIndex, ipDeviceAddress, ipDeviceDescription, ipDeviceValue, ipDeviceStatus }
    STATUS              current
    DESCRIPTION         "Trap issued when IP device #26 has a notification to send"
    ::= { ipDevicesTraps 0 26 }

ipDevice27Trap          NOTIFICATION-TYPE    
    OBJECTS             { envTrapDescription, ipDeviceIndex, ipDeviceAddress, ipDeviceDescription, ipDeviceValue, ipDeviceStatus }
    STATUS              current
    DESCRIPTION         "Trap issued when IP device #27 has a notification to send"
    ::= { ipDevicesTraps 0 27 }

ipDevice28Trap          NOTIFICATION-TYPE    
    OBJECTS             { envTrapDescription, ipDeviceIndex, ipDeviceAddress, ipDeviceDescription, ipDeviceValue, ipDeviceStatus }
    STATUS              current
    DESCRIPTION         "Trap issued when IP device #28 has a notification to send"
    ::= { ipDevicesTraps 0 28 }

ipDevice29Trap          NOTIFICATION-TYPE    
    OBJECTS             { envTrapDescription, ipDeviceIndex, ipDeviceAddress, ipDeviceDescription, ipDeviceValue, ipDeviceStatus }
    STATUS              current
    DESCRIPTION         "Trap issued when IP device #29 has a notification to send"
    ::= { ipDevicesTraps 0 29 }

ipDevice30Trap          NOTIFICATION-TYPE    
    OBJECTS             { envTrapDescription, ipDeviceIndex, ipDeviceAddress, ipDeviceDescription, ipDeviceValue, ipDeviceStatus }
    STATUS              current
    DESCRIPTION         "Trap issued when IP device #30 has a notification to send"
    ::= { ipDevicesTraps 0 30 }

ipDevice31Trap          NOTIFICATION-TYPE    
    OBJECTS             { envTrapDescription, ipDeviceIndex, ipDeviceAddress, ipDeviceDescription, ipDeviceValue, ipDeviceStatus }
    STATUS              current
    DESCRIPTION         "Trap issued when IP device #31 has a notification to send"
    ::= { ipDevicesTraps 0 31 }

ipDevice32Trap          NOTIFICATION-TYPE    
    OBJECTS             { envTrapDescription, ipDeviceIndex, ipDeviceAddress, ipDeviceDescription, ipDeviceValue, ipDeviceStatus }
    STATUS              current
    DESCRIPTION         "Trap issued when IP device #32 has a notification to send"
    ::= { ipDevicesTraps 0 32 }

ipDevice33Trap           NOTIFICATION-TYPE    
    OBJECTS             { envTrapDescription, ipDeviceIndex, ipDeviceAddress, ipDeviceDescription, ipDeviceValue, ipDeviceStatus }
    STATUS              current
    DESCRIPTION         "Trap issued when IP device #33 has a notification to send"
    ::= { ipDevicesTraps 0 33 }

ipDevice34Trap           NOTIFICATION-TYPE    
    OBJECTS             { envTrapDescription, ipDeviceIndex, ipDeviceAddress, ipDeviceDescription, ipDeviceValue, ipDeviceStatus }
    STATUS              current
    DESCRIPTION         "Trap issued when IP device #34 has a notification to send"
    ::= { ipDevicesTraps 0 34 }

ipDevice35Trap           NOTIFICATION-TYPE    
    OBJECTS             { envTrapDescription, ipDeviceIndex, ipDeviceAddress, ipDeviceDescription, ipDeviceValue, ipDeviceStatus }
    STATUS              current
    DESCRIPTION         "Trap issued when IP device #35 has a notification to send"
    ::= { ipDevicesTraps 0 35 }

ipDevice36Trap           NOTIFICATION-TYPE    
    OBJECTS             { envTrapDescription, ipDeviceIndex, ipDeviceAddress, ipDeviceDescription, ipDeviceValue, ipDeviceStatus }
    STATUS              current
    DESCRIPTION         "Trap issued when IP device #36 has a notification to send"
    ::= { ipDevicesTraps 0 36 }

ipDevice37Trap           NOTIFICATION-TYPE    
    OBJECTS             { envTrapDescription, ipDeviceIndex, ipDeviceAddress, ipDeviceDescription, ipDeviceValue, ipDeviceStatus }
    STATUS              current
    DESCRIPTION         "Trap issued when IP device #37 has a notification to send"
    ::= { ipDevicesTraps 0 37 }

ipDevice38Trap           NOTIFICATION-TYPE    
    OBJECTS             { envTrapDescription, ipDeviceIndex, ipDeviceAddress, ipDeviceDescription, ipDeviceValue, ipDeviceStatus }
    STATUS              current
    DESCRIPTION         "Trap issued when IP device #38 has a notification to send"
    ::= { ipDevicesTraps 0 38 }

ipDevice39Trap           NOTIFICATION-TYPE    
    OBJECTS             { envTrapDescription, ipDeviceIndex, ipDeviceAddress, ipDeviceDescription, ipDeviceValue, ipDeviceStatus }
    STATUS              current
    DESCRIPTION         "Trap issued when IP device #39 has a notification to send"
    ::= { ipDevicesTraps 0 39 }

ipDevice40Trap           NOTIFICATION-TYPE    
    OBJECTS             { envTrapDescription, ipDeviceIndex, ipDeviceAddress, ipDeviceDescription, ipDeviceValue, ipDeviceStatus }
    STATUS              current
    DESCRIPTION         "Trap issued when IP device #40 has a notification to send"
    ::= { ipDevicesTraps 0 40 }

ipDevice41Trap           NOTIFICATION-TYPE    
    OBJECTS             { envTrapDescription, ipDeviceIndex, ipDeviceAddress, ipDeviceDescription, ipDeviceValue, ipDeviceStatus }
    STATUS              current
    DESCRIPTION         "Trap issued when IP device #41 has a notification to send"
    ::= { ipDevicesTraps 0 41 }

ipDevice42Trap          NOTIFICATION-TYPE    
    OBJECTS             { envTrapDescription, ipDeviceIndex, ipDeviceAddress, ipDeviceDescription, ipDeviceValue, ipDeviceStatus }
    STATUS              current
    DESCRIPTION         "Trap issued when IP device #42 has a notification to send"
    ::= { ipDevicesTraps 0 42 }

ipDevice43Trap          NOTIFICATION-TYPE    
    OBJECTS             { envTrapDescription, ipDeviceIndex, ipDeviceAddress, ipDeviceDescription, ipDeviceValue, ipDeviceStatus }
    STATUS              current
    DESCRIPTION         "Trap issued when IP device #43 has a notification to send"
    ::= { ipDevicesTraps 0 43 }

ipDevice44Trap          NOTIFICATION-TYPE    
    OBJECTS             { envTrapDescription, ipDeviceIndex, ipDeviceAddress, ipDeviceDescription, ipDeviceValue, ipDeviceStatus }
    STATUS              current
    DESCRIPTION         "Trap issued when IP device #44 has a notification to send"
    ::= { ipDevicesTraps 0 44 }

ipDevice45Trap          NOTIFICATION-TYPE    
    OBJECTS             { envTrapDescription, ipDeviceIndex, ipDeviceAddress, ipDeviceDescription, ipDeviceValue, ipDeviceStatus }
    STATUS              current
    DESCRIPTION         "Trap issued when IP device #45 has a notification to send"
    ::= { ipDevicesTraps 0 45 }

ipDevice46Trap          NOTIFICATION-TYPE    
    OBJECTS             { envTrapDescription, ipDeviceIndex, ipDeviceAddress, ipDeviceDescription, ipDeviceValue, ipDeviceStatus }
    STATUS              current
    DESCRIPTION         "Trap issued when IP device #46 has a notification to send"
    ::= { ipDevicesTraps 0 46 }

ipDevice47Trap          NOTIFICATION-TYPE    
    OBJECTS             { envTrapDescription, ipDeviceIndex, ipDeviceAddress, ipDeviceDescription, ipDeviceValue, ipDeviceStatus }
    STATUS              current
    DESCRIPTION         "Trap issued when IP device #47 has a notification to send"
    ::= { ipDevicesTraps 0 47 }

ipDevice48Trap          NOTIFICATION-TYPE    
    OBJECTS             { envTrapDescription, ipDeviceIndex, ipDeviceAddress, ipDeviceDescription, ipDeviceValue, ipDeviceStatus }
    STATUS              current
    DESCRIPTION         "Trap issued when IP device #48 has a notification to send"
    ::= { ipDevicesTraps 0 48 }

ipDevice49Trap           NOTIFICATION-TYPE    
    OBJECTS             { envTrapDescription, ipDeviceIndex, ipDeviceAddress, ipDeviceDescription, ipDeviceValue, ipDeviceStatus }
    STATUS              current
    DESCRIPTION         "Trap issued when IP device #49 has a notification to send"
    ::= { ipDevicesTraps 0 49 }

ipDevice50Trap           NOTIFICATION-TYPE    
    OBJECTS             { envTrapDescription, ipDeviceIndex, ipDeviceAddress, ipDeviceDescription, ipDeviceValue, ipDeviceStatus }
    STATUS              current
    DESCRIPTION         "Trap issued when IP device #50 has a notification to send"
    ::= { ipDevicesTraps 0 50 }

ipDevice51Trap           NOTIFICATION-TYPE    
    OBJECTS             { envTrapDescription, ipDeviceIndex, ipDeviceAddress, ipDeviceDescription, ipDeviceValue, ipDeviceStatus }
    STATUS              current
    DESCRIPTION         "Trap issued when IP device #51 has a notification to send"
    ::= { ipDevicesTraps 0 51 }

ipDevice52Trap           NOTIFICATION-TYPE    
    OBJECTS             { envTrapDescription, ipDeviceIndex, ipDeviceAddress, ipDeviceDescription, ipDeviceValue, ipDeviceStatus }
    STATUS              current
    DESCRIPTION         "Trap issued when IP device #52 has a notification to send"
    ::= { ipDevicesTraps 0 52 }

ipDevice53Trap           NOTIFICATION-TYPE    
    OBJECTS             { envTrapDescription, ipDeviceIndex, ipDeviceAddress, ipDeviceDescription, ipDeviceValue, ipDeviceStatus }
    STATUS              current
    DESCRIPTION         "Trap issued when IP device #53 has a notification to send"
    ::= { ipDevicesTraps 0 53 }

ipDevice54Trap           NOTIFICATION-TYPE    
    OBJECTS             { envTrapDescription, ipDeviceIndex, ipDeviceAddress, ipDeviceDescription, ipDeviceValue, ipDeviceStatus }
    STATUS              current
    DESCRIPTION         "Trap issued when IP device #54 has a notification to send"
    ::= { ipDevicesTraps 0 54 }

ipDevice55Trap           NOTIFICATION-TYPE    
    OBJECTS             { envTrapDescription, ipDeviceIndex, ipDeviceAddress, ipDeviceDescription, ipDeviceValue, ipDeviceStatus }
    STATUS              current
    DESCRIPTION         "Trap issued when IP device #55 has a notification to send"
    ::= { ipDevicesTraps 0 55 }

ipDevice56Trap           NOTIFICATION-TYPE    
    OBJECTS             { envTrapDescription, ipDeviceIndex, ipDeviceAddress, ipDeviceDescription, ipDeviceValue, ipDeviceStatus }
    STATUS              current
    DESCRIPTION         "Trap issued when IP device #56 has a notification to send"
    ::= { ipDevicesTraps 0 56 }

ipDevice57Trap           NOTIFICATION-TYPE    
    OBJECTS             { envTrapDescription, ipDeviceIndex, ipDeviceAddress, ipDeviceDescription, ipDeviceValue, ipDeviceStatus }
    STATUS              current
    DESCRIPTION         "Trap issued when IP device #57 has a notification to send"
    ::= { ipDevicesTraps 0 57 }

ipDevice58Trap          NOTIFICATION-TYPE    
    OBJECTS             { envTrapDescription, ipDeviceIndex, ipDeviceAddress, ipDeviceDescription, ipDeviceValue, ipDeviceStatus }
    STATUS              current
    DESCRIPTION         "Trap issued when IP device #58 has a notification to send"
    ::= { ipDevicesTraps 0 58 }

ipDevice59Trap          NOTIFICATION-TYPE    
    OBJECTS             { envTrapDescription, ipDeviceIndex, ipDeviceAddress, ipDeviceDescription, ipDeviceValue, ipDeviceStatus }
    STATUS              current
    DESCRIPTION         "Trap issued when IP device #59 has a notification to send"
    ::= { ipDevicesTraps 0 59 }

ipDevice60Trap          NOTIFICATION-TYPE    
    OBJECTS             { envTrapDescription, ipDeviceIndex, ipDeviceAddress, ipDeviceDescription, ipDeviceValue, ipDeviceStatus }
    STATUS              current
    DESCRIPTION         "Trap issued when IP device #60 has a notification to send"
    ::= { ipDevicesTraps 0 60 }

ipDevice61Trap          NOTIFICATION-TYPE    
    OBJECTS             { envTrapDescription, ipDeviceIndex, ipDeviceAddress, ipDeviceDescription, ipDeviceValue, ipDeviceStatus }
    STATUS              current
    DESCRIPTION         "Trap issued when IP device #61 has a notification to send"
    ::= { ipDevicesTraps 0 61 }

ipDevice62Trap          NOTIFICATION-TYPE    
    OBJECTS             { envTrapDescription, ipDeviceIndex, ipDeviceAddress, ipDeviceDescription, ipDeviceValue, ipDeviceStatus }
    STATUS              current
    DESCRIPTION         "Trap issued when IP device #62 has a notification to send"
    ::= { ipDevicesTraps 0 62 }

ipDevice63Trap          NOTIFICATION-TYPE    
    OBJECTS             { envTrapDescription, ipDeviceIndex, ipDeviceAddress, ipDeviceDescription, ipDeviceValue, ipDeviceStatus }
    STATUS              current
    DESCRIPTION         "Trap issued when IP device #63 has a notification to send"
    ::= { ipDevicesTraps 0 63 }

ipDevice64Trap          NOTIFICATION-TYPE    
    OBJECTS             { envTrapDescription, ipDeviceIndex, ipDeviceAddress, ipDeviceDescription, ipDeviceValue, ipDeviceStatus }
    STATUS              current
    DESCRIPTION         "Trap issued when IP device #64 has a notification to send"
    ::= { ipDevicesTraps 0 64 }

-- Output Relay trap

outRelay1Trap           NOTIFICATION-TYPE
    OBJECTS             { envTrapDescription, outRelayIndex, outRelayDescription, outRelayStatus }
    STATUS              current
    DESCRIPTION         "Trap issued when output relay changes it's status"
    ::= { outRelaysTraps 0 1 }
    
-- Event Log file trap

evLogFileTrap           NOTIFICATION-TYPE
    OBJECTS             { envTrapDescription }
    STATUS              current
    DESCRIPTION         "Trap issued when the system has an event log file notification to send"
    ::= { envTraps 0 10 }

-- Data Log file trap

dataLogFileTrap         NOTIFICATION-TYPE
    OBJECTS             { envTrapDescription }
    STATUS              current
    DESCRIPTION         "Trap issued when the system has a data log file notification to send (file almost full)"
    ::= { envTraps 0 11 }

remoteDataLogFileTrap   NOTIFICATION-TYPE
    OBJECTS             { envTrapDescription, envTrapValue }
    STATUS              current
    DESCRIPTION         "Trap issued when the system has a data log file reading to send"
    ::= { envTraps 0 12 }
    
-- Smoke Detectors
smokeDetector1Trap      NOTIFICATION-TYPE
    OBJECTS             { envTrapDescription, smokeDetectorIndex, smokeDetectorDescription, smokeDetectorValue, smokeDetectorStatus }
    STATUS              current
    DESCRIPTION         "Trap issued when smoke detector changes it's status"
    ::= { smokeDetectorsTraps 0 1 }
    
smokeDetector2Trap      NOTIFICATION-TYPE
    OBJECTS             { envTrapDescription, smokeDetectorIndex, smokeDetectorDescription, smokeDetectorValue, smokeDetectorStatus }
    STATUS              current
    DESCRIPTION         "Trap issued when smoke detector changes it's status"
    ::= { smokeDetectorsTraps 0 2 }
    
smokeDetector3Trap      NOTIFICATION-TYPE
    OBJECTS             { envTrapDescription, smokeDetectorIndex, smokeDetectorDescription, smokeDetectorValue, smokeDetectorStatus }
    STATUS              current
    DESCRIPTION         "Trap issued when smoke detector changes it's status"
    ::= { smokeDetectorsTraps 0 3 }
    
smokeDetector4Trap      NOTIFICATION-TYPE
    OBJECTS             { envTrapDescription, smokeDetectorIndex, smokeDetectorDescription, smokeDetectorValue, smokeDetectorStatus }
    STATUS              current
    DESCRIPTION         "Trap issued when smoke detector changes it's status"
    ::= { smokeDetectorsTraps 0 4 }
    
smokeDetector5Trap      NOTIFICATION-TYPE
    OBJECTS             { envTrapDescription, smokeDetectorIndex, smokeDetectorDescription, smokeDetectorValue, smokeDetectorStatus }
    STATUS              current
    DESCRIPTION         "Trap issued when smoke detector changes it's status"
    ::= { smokeDetectorsTraps 0 5 }
    
smokeDetector6Trap      NOTIFICATION-TYPE
    OBJECTS             { envTrapDescription, smokeDetectorIndex, smokeDetectorDescription, smokeDetectorValue, smokeDetectorStatus }
    STATUS              current
    DESCRIPTION         "Trap issued when smoke detector changes it's status"
    ::= { smokeDetectorsTraps 0 6 }
    
smokeDetector7Trap      NOTIFICATION-TYPE
    OBJECTS             { envTrapDescription, smokeDetectorIndex, smokeDetectorDescription, smokeDetectorValue, smokeDetectorStatus }
    STATUS              current
    DESCRIPTION         "Trap issued when smoke detector changes it's status"
    ::= { smokeDetectorsTraps 0 7 }
    
smokeDetector8Trap      NOTIFICATION-TYPE
    OBJECTS             { envTrapDescription, smokeDetectorIndex, smokeDetectorDescription, smokeDetectorValue, smokeDetectorStatus }
    STATUS              current
    DESCRIPTION         "Trap issued when smoke detector changes it's status"
    ::= { smokeDetectorsTraps 0 8 }

- remote Input traps

remoteInput1Trap         NOTIFICATION-TYPE
    OBJECTS             { envTrapDescription, remoteInputIndex, remoteInputDescription, remoteInputValue, remoteInputStatus }
    STATUS              current    DESCRIPTION         "Trap issued when remote digital input 1 has a notification to send"
    ::= {remoteInputsTraps 0 1 }

remoteInput2Trap         NOTIFICATION-TYPE
    OBJECTS             { envTrapDescription, remoteInputIndex, remoteInputDescription, remoteInputValue, remoteInputStatus }
    STATUS              current    DESCRIPTION         "Trap issued when remote digital input 2 has a notification to send"
    ::= {remoteInputsTraps 0 2 }

remoteInput3Trap         NOTIFICATION-TYPE
    OBJECTS             { envTrapDescription, remoteInputIndex, remoteInputDescription, remoteInputValue, remoteInputStatus }
    STATUS              current    DESCRIPTION         "Trap issued when remote digital input 3 has a notification to send"
    ::= {remoteInputsTraps 0 3 }

remoteInput4Trap         NOTIFICATION-TYPE
    OBJECTS             { envTrapDescription, remoteInputIndex, remoteInputDescription, remoteInputValue, remoteInputStatus }
    STATUS              current    DESCRIPTION         "Trap issued when remote digital input 4 has a notification to send"
    ::= {remoteInputsTraps 0 4 }

remoteInput5Trap         NOTIFICATION-TYPE
    OBJECTS             { envTrapDescription, remoteInputIndex, remoteInputDescription, remoteInputValue, remoteInputStatus }
    STATUS              current    DESCRIPTION         "Trap issued when remote digital input 5 has a notification to send"
    ::= {remoteInputsTraps 0 5 }

remoteInput6Trap         NOTIFICATION-TYPE
    OBJECTS             { envTrapDescription, remoteInputIndex, remoteInputDescription, remoteInputValue, remoteInputStatus }
    STATUS              current    DESCRIPTION         "Trap issued when remote digital input 6 has a notification to send"
    ::= {remoteInputsTraps 0 6 }

remoteInput7Trap         NOTIFICATION-TYPE
    OBJECTS             { envTrapDescription, remoteInputIndex, remoteInputDescription, remoteInputValue, remoteInputStatus }
    STATUS              current    DESCRIPTION         "Trap issued when remote digital input 7 has a notification to send"
    ::= {remoteInputsTraps 0 7 }

remoteInput8Trap         NOTIFICATION-TYPE
    OBJECTS             { envTrapDescription, remoteInputIndex, remoteInputDescription, remoteInputValue, remoteInputStatus }
    STATUS              current    DESCRIPTION         "Trap issued when remote digital input 8 has a notification to send"
    ::= {remoteInputsTraps 0 8 }

remoteInput9Trap         NOTIFICATION-TYPE
    OBJECTS             { envTrapDescription, remoteInputIndex, remoteInputDescription, remoteInputValue, remoteInputStatus }
    STATUS              current    DESCRIPTION         "Trap issued when remote digital input 9 has a notification to send"
    ::= {remoteInputsTraps 0 9 }

remoteInput10Trap         NOTIFICATION-TYPE
    OBJECTS             { envTrapDescription, remoteInputIndex, remoteInputDescription, remoteInputValue, remoteInputStatus }
    STATUS              current    DESCRIPTION         "Trap issued when remote digital input 10 has a notification to send"
    ::= {remoteInputsTraps 0 10 }

remoteInput11Trap         NOTIFICATION-TYPE
    OBJECTS             { envTrapDescription, remoteInputIndex, remoteInputDescription, remoteInputValue, remoteInputStatus }
    STATUS              current    DESCRIPTION         "Trap issued when remote digital input 11 has a notification to send"
    ::= {remoteInputsTraps 0 11 }

remoteInput12Trap         NOTIFICATION-TYPE
    OBJECTS             { envTrapDescription, remoteInputIndex, remoteInputDescription, remoteInputValue, remoteInputStatus }
    STATUS              current    DESCRIPTION         "Trap issued when remote digital input 12 has a notification to send"
    ::= {remoteInputsTraps 0 12 }

remoteInput13Trap         NOTIFICATION-TYPE
    OBJECTS             { envTrapDescription, remoteInputIndex, remoteInputDescription, remoteInputValue, remoteInputStatus }
    STATUS              current    DESCRIPTION         "Trap issued when remote digital input 13 has a notification to send"
    ::= {remoteInputsTraps 0 13 }

remoteInput14Trap         NOTIFICATION-TYPE
    OBJECTS             { envTrapDescription, remoteInputIndex, remoteInputDescription, remoteInputValue, remoteInputStatus }
    STATUS              current    DESCRIPTION         "Trap issued when remote digital input 14 has a notification to send"
    ::= {remoteInputsTraps 0 14 }

remoteInput15Trap         NOTIFICATION-TYPE
    OBJECTS             { envTrapDescription, remoteInputIndex, remoteInputDescription, remoteInputValue, remoteInputStatus }
    STATUS              current    DESCRIPTION         "Trap issued when remote digital input 15 has a notification to send"
    ::= {remoteInputsTraps 0 15 }

remoteInput16Trap         NOTIFICATION-TYPE
    OBJECTS             { envTrapDescription, remoteInputIndex, remoteInputDescription, remoteInputValue, remoteInputStatus }
    STATUS              current    DESCRIPTION         "Trap issued when remote digital input 16 has a notification to send"
    ::= {remoteInputsTraps 0 16 }

--remote output relay traps

remoteRelay1Trap         NOTIFICATION-TYPE
    OBJECTS             { envTrapDescription, remoteRelayIndex, remoteRelayDescription, remoteRelayStatus }
    STATUS              current    DESCRIPTION         "Trap issued when remote output relay changes it's status"
    ::= {remoteRelaysTraps 0 1 }

remoteRelay2Trap         NOTIFICATION-TYPE
    OBJECTS             { envTrapDescription, remoteRelayIndex, remoteRelayDescription, remoteRelayStatus }
    STATUS              current    DESCRIPTION         "Trap issued when remote output relay changes it's status"
    ::= {remoteRelaysTraps 0 2 }

remoteRelay3Trap         NOTIFICATION-TYPE
    OBJECTS             { envTrapDescription, remoteRelayIndex, remoteRelayDescription, remoteRelayStatus }
    STATUS              current    DESCRIPTION         "Trap issued when remote output relay changes it's status"
    ::= {remoteRelaysTraps 0 3 }

remoteRelay4Trap         NOTIFICATION-TYPE
    OBJECTS             { envTrapDescription, remoteRelayIndex, remoteRelayDescription, remoteRelayStatus }
    STATUS              current    DESCRIPTION         "Trap issued when remote output relay changes it's status"
    ::= {remoteRelaysTraps 0 4 }

remoteRelay5Trap         NOTIFICATION-TYPE
    OBJECTS             { envTrapDescription, remoteRelayIndex, remoteRelayDescription, remoteRelayStatus }
    STATUS              current    DESCRIPTION         "Trap issued when remote output relay changes it's status"
    ::= {remoteRelaysTraps 0 5 }

remoteRelay6Trap         NOTIFICATION-TYPE
    OBJECTS             { envTrapDescription, remoteRelayIndex, remoteRelayDescription, remoteRelayStatus }
    STATUS              current    DESCRIPTION         "Trap issued when remote output relay changes it's status"
    ::= {remoteRelaysTraps 0 6 }

remoteRelay7Trap         NOTIFICATION-TYPE
    OBJECTS             { envTrapDescription, remoteRelayIndex, remoteRelayDescription, remoteRelayStatus }
    STATUS              current    DESCRIPTION         "Trap issued when remote output relay changes it's status"
    ::= {remoteRelaysTraps 0 7 }

remoteRelay8Trap         NOTIFICATION-TYPE
    OBJECTS             { envTrapDescription, remoteRelayIndex, remoteRelayDescription, remoteRelayStatus }
    STATUS              current    DESCRIPTION         "Trap issued when remote output relay changes it's status"
    ::= {remoteRelaysTraps 0 8 }

remoteRelay9Trap         NOTIFICATION-TYPE
    OBJECTS             { envTrapDescription, remoteRelayIndex, remoteRelayDescription, remoteRelayStatus }
    STATUS              current    DESCRIPTION         "Trap issued when remote output relay changes it's status"
    ::= {remoteRelaysTraps 0 9 }

remoteRelay10Trap         NOTIFICATION-TYPE
    OBJECTS             { envTrapDescription, remoteRelayIndex, remoteRelayDescription, remoteRelayStatus }
    STATUS              current    DESCRIPTION         "Trap issued when remote output relay changes it's status"
    ::= {remoteRelaysTraps 0 10 }

remoteRelay11Trap         NOTIFICATION-TYPE
    OBJECTS             { envTrapDescription, remoteRelayIndex, remoteRelayDescription, remoteRelayStatus }
    STATUS              current    DESCRIPTION         "Trap issued when remote output relay changes it's status"
    ::= {remoteRelaysTraps 0 11 }

remoteRelay12Trap         NOTIFICATION-TYPE
    OBJECTS             { envTrapDescription, remoteRelayIndex, remoteRelayDescription, remoteRelayStatus }
    STATUS              current    DESCRIPTION         "Trap issued when remote output relay changes it's status"
    ::= {remoteRelaysTraps 0 12 }

remoteRelay13Trap         NOTIFICATION-TYPE
    OBJECTS             { envTrapDescription, remoteRelayIndex, remoteRelayDescription, remoteRelayStatus }
    STATUS              current    DESCRIPTION         "Trap issued when remote output relay changes it's status"
    ::= {remoteRelaysTraps 0 13 }

remoteRelay14Trap         NOTIFICATION-TYPE
    OBJECTS             { envTrapDescription, remoteRelayIndex, remoteRelayDescription, remoteRelayStatus }
    STATUS              current    DESCRIPTION         "Trap issued when remote output relay changes it's status"
    ::= {remoteRelaysTraps 0 14 }

remoteRelay15Trap         NOTIFICATION-TYPE
    OBJECTS             { envTrapDescription, remoteRelayIndex, remoteRelayDescription, remoteRelayStatus }
    STATUS              current    DESCRIPTION         "Trap issued when remote output relay changes it's status"
    ::= {remoteRelaysTraps 0 15 }

remoteRelay16Trap         NOTIFICATION-TYPE
    OBJECTS             { envTrapDescription, remoteRelayIndex, remoteRelayDescription, remoteRelayStatus }
    STATUS              current    DESCRIPTION         "Trap issued when remote output relay changes it's status"
    ::= {remoteRelaysTraps 0 16 }
    

END
